--
-- NSCRTV-PON-TREE-EXT-MIB.my
-- MIB generated by MG-SOFT Visual MIB Builder Version 6.0  Build 88
-- Monday, July 01, 2024 at 14:38:47
--

	NSCRTV-PON-TREE-EXT-MIB DEFINITIONS ::= BEGIN
 
		IMPORTS
			Ipv6Address			
				FROM IPV6-TC			
			IpAddress, Integer32, Unsigned32, Counter64, OBJECT-TYPE, 
			MODULE-IDENTITY, OBJECT-IDENTITY			
				FROM SNMPv2-SMI			
			TruthValue, RowStatus, DisplayString, DateAndTime, MacAddress, 
			TEXTUAL-CONVENTION			
				FROM SNMPv2-TC			
			pon, NscrtvPonExtDeviceIndex, NscrtvPonExtCardIndex, NscrtvPonPortIndex, NscrtvPonExtEtherType, 
			NscrtvPonExtAdminStatus, NscrtvPonExtOnuOnlineState, NscrtvPonExtVlanTagAction, NscrtvPonExtAutoMode			
				FROM VENDOR-COMMON-MIB;
	
	
		-- 1.3.6.1.4.1.34592.1.3.100
		nscrtvPonTreeExt MODULE-IDENTITY 
			LAST-UPDATED ""		-- 
			ORGANIZATION 
				"Organization."
			CONTACT-INFO 
				"Contact-info."
			DESCRIPTION 
				"Description."
			::= { pon 100 }

		
	
--
-- Textual conventions
--
	
		EponDeviceIndex ::= TEXTUAL-CONVENTION
			STATUS current
			DESCRIPTION 
				"
				Epon olt/onu设备索引号。       
				ONU ID的组成(4字节)(高--低)          
				Olt device-8bit OLT Card-8bit Pon port-8bit OnuNUM-8bit        
				Note: 
				----        
				1. OLT device must not be 0.        
				2. Card here shall confirm the last byte definition of EponCardIndex
				   to indicate the main-slot and sub-slot index.         
				3. Pon port must not be 0.
				4. The useful ONU logical ID MUST never be set to 0, where NUM of 0 has
				   another meaning, to indicate that the ONU logical ID is meaningless,
				   or said to not applied.
				        
				Usage guide:
				-----------        
				This TC could be used for OLT SNI, OLT PON port, OLT ONU ID
				OLT device, hybrid.         
				If the refered MIB object does not have clear definition,
				refer to the following:
				Applied Obj  - Descriptions of Index
				------------------------------------------------------------------
				OLT Pon Port - OnuNum shall be set to 0,
				OLT SNI    - Same as OLT Pon Port         
				OLT onu ID   - Set OnuNUM to corresponding ONU logical ID         
				OLT device   - Set card, pon port and OnuNUM to 0
				Hybrid    - Card to 0x3F, pon port to hybrid ID, OnuNUM to 0
				         Olt device to corresponding ONU device       
				"
			SYNTAX Unsigned32

		EponCardIndex ::= TEXTUAL-CONVENTION
			STATUS current
			DESCRIPTION 
				"
				板卡索引号        
				For easy presenting the chassis view by NMS, bCardIndex shall be formatted
				in a following manner:                        
				    Four bytes of INTEGER, from the most significant byte to the least significant
				    bytes
				        -----------------------------------------------------------------------------
				Reserved byte Reserved byte   Reserved byte Sub-slot 2-bit Main-slot 6-bit        
				Notes:
				-----         
				1. Reserved bytes shall be set to 0.        
				2. The main-slot shall be started from 1, and shall be in a consecutive manner,
				   for all slots, including service slots, control slots, switch slots, power
				slots,FAN slots, etc.For example, 1, 2, 3          
				3. The sub-slot shall be started from 1, and shall be in a consecutive manner.
				   For example, 1, 2. If no sub-slot concept of a main-slot, set to 0.        
				4. For fixed device, if no slot concept, NE shall set both main-slot and sub-slot
				to 0, to indicate this is meaningless. For modulized device, they MUST not be
				set to 0.This definition shall applied to both OLT and ONU.        
				5. For hybrid, since there is no slot concept, set main-slot to all-1 and sub-slot
				to 0. This definition shall applied to both OLT and ONU.
				
				For example, 
				0x00 00 00 0A, represents main-slot 10, no sub-slot
				0x00 00 00 42, represents main-slot 2, sub-slot 1
				0x00 00 00 3F, represents a hybrid
				"
			SYNTAX Unsigned32

	
--
-- Node definitions
--
	
		-- 1.3.6.1.4.1.34592.1.3.100.1
		systemObjects OBJECT IDENTIFIER ::= { nscrtvPonTreeExt 1 }

		
		-- 1.3.6.1.4.1.34592.1.3.100.1.1
		configManagementObjects OBJECT-IDENTITY
			STATUS current
			DESCRIPTION 
				"配置管理"
			::= { systemObjects 1 }

		
		-- 1.3.6.1.4.1.34592.1.3.100.1.1.1
		configOperation OBJECT-TYPE
			SYNTAX INTEGER
				{
				import(1),
				export(2),
				default(3)
				}
			MAX-ACCESS read-write
			STATUS current
			DESCRIPTION
				"
				import device configuration when set value to 1.
				export device configuration when set value to 2.
				default device configuration when set value to 3.
				"
			::= { configManagementObjects 1 }

		
		-- 1.3.6.1.4.1.34592.1.3.100.1.1.2
		configfile OBJECT-TYPE
			SYNTAX OCTET STRING
			MAX-ACCESS read-write
			STATUS current
			DESCRIPTION
				" configuration file name"
			::= { configManagementObjects 2 }

		
		-- 1.3.6.1.4.1.34592.1.3.100.1.1.3
		configStatus OBJECT-TYPE
			SYNTAX INTEGER
				{
				fail(0),
				idle(1),
				inProcess(2),
				success(3)
				}
			MAX-ACCESS read-only
			STATUS current
			DESCRIPTION
				"
				import device configuration status "
			::= { configManagementObjects 3 }

		
		-- 1.3.6.1.4.1.34592.1.3.100.1.2
		interfaceManagementObjects OBJECT-IDENTITY
			STATUS current
			DESCRIPTION 
				"接口管理"
			::= { systemObjects 2 }

		
		-- 1.3.6.1.4.1.34592.1.3.100.1.2.1
		inBandInterfaceTable OBJECT-TYPE
			SYNTAX SEQUENCE OF InBandInterfaceEntry
			MAX-ACCESS not-accessible
			STATUS current
			DESCRIPTION
				"Description."
			::= { interfaceManagementObjects 1 }

		
		-- 1.3.6.1.4.1.34592.1.3.100.1.2.1.1
		inBandInterfaceEntry OBJECT-TYPE
			SYNTAX InBandInterfaceEntry
			MAX-ACCESS not-accessible
			STATUS current
			DESCRIPTION
				"Description."
			INDEX { inBandInterfaceVlanIdIndex }
			::= { inBandInterfaceTable 1 }

		
		InBandInterfaceEntry ::=
			SEQUENCE { 
				inBandInterfaceVlanIdIndex
					INTEGER,
				inBandInterfaceIP
					IpAddress,
				inBandInterfaceMask
					IpAddress,
				inBandInterfaceGateway
					IpAddress,
				inBandInterfaceLinkStatus
					INTEGER,
				inBandInterfaceEnable
					TruthValue,
				inBandInterfaceDesc
					OCTET STRING,
				inBandInterfaceRowStatus
					RowStatus
			 }

		-- 1.3.6.1.4.1.34592.1.3.100.1.2.1.1.1
		inBandInterfaceVlanIdIndex OBJECT-TYPE
			SYNTAX INTEGER
			MAX-ACCESS not-accessible
			STATUS current
			DESCRIPTION
				"带内管理接口VLAN ID.
				
				带内管理VLAN的成员关系由VLAN表定义"
			::= { inBandInterfaceEntry 1 }

		
		-- 1.3.6.1.4.1.34592.1.3.100.1.2.1.1.2
		inBandInterfaceIP OBJECT-TYPE
			SYNTAX IpAddress
			MAX-ACCESS read-create
			STATUS current
			DESCRIPTION
				"
				带内管理接口IP地址"
			::= { inBandInterfaceEntry 2 }

		
		-- 1.3.6.1.4.1.34592.1.3.100.1.2.1.1.3
		inBandInterfaceMask OBJECT-TYPE
			SYNTAX IpAddress
			MAX-ACCESS read-create
			STATUS current
			DESCRIPTION
				"
				带内管理接口IP掩码"
			::= { inBandInterfaceEntry 3 }

		
		-- 1.3.6.1.4.1.34592.1.3.100.1.2.1.1.4
		inBandInterfaceGateway OBJECT-TYPE
			SYNTAX IpAddress
			MAX-ACCESS read-create
			STATUS current
			DESCRIPTION
				"
				带内管理接口网关IP地址"
			::= { inBandInterfaceEntry 4 }

		
		-- 1.3.6.1.4.1.34592.1.3.100.1.2.1.1.5
		inBandInterfaceLinkStatus OBJECT-TYPE
			SYNTAX INTEGER
				{
				up(1),
				down(2)
				}
			MAX-ACCESS read-only
			STATUS current
			DESCRIPTION
				" link status "
			::= { inBandInterfaceEntry 5 }

		
		-- 1.3.6.1.4.1.34592.1.3.100.1.2.1.1.6
		inBandInterfaceEnable OBJECT-TYPE
			SYNTAX TruthValue
			MAX-ACCESS read-create
			STATUS current
			DESCRIPTION
				"Description."
			::= { inBandInterfaceEntry 6 }

		
		-- 1.3.6.1.4.1.34592.1.3.100.1.2.1.1.7
		inBandInterfaceDesc OBJECT-TYPE
			SYNTAX OCTET STRING
			MAX-ACCESS read-create
			STATUS current
			DESCRIPTION
				" Description "
			::= { inBandInterfaceEntry 7 }

		
		-- 1.3.6.1.4.1.34592.1.3.100.1.2.1.1.8
		inBandInterfaceRowStatus OBJECT-TYPE
			SYNTAX RowStatus
			MAX-ACCESS read-create
			STATUS current
			DESCRIPTION
				"RowStatus."
			::= { inBandInterfaceEntry 8 }

		
		-- 1.3.6.1.4.1.34592.1.3.100.1.2.2
		outBandInterfaceTable OBJECT-TYPE
			SYNTAX SEQUENCE OF OutBandInterfaceEntry
			MAX-ACCESS not-accessible
			STATUS current
			DESCRIPTION
				"Description."
			::= { interfaceManagementObjects 2 }

		
		-- 1.3.6.1.4.1.34592.1.3.100.1.2.2.1
		outBandInterfaceEntry OBJECT-TYPE
			SYNTAX OutBandInterfaceEntry
			MAX-ACCESS not-accessible
			STATUS current
			DESCRIPTION
				"Description."
			INDEX { outBandInterfaceDeviceIndex }
			::= { outBandInterfaceTable 1 }

		
		OutBandInterfaceEntry ::=
			SEQUENCE { 
				outBandInterfaceDeviceIndex
					NscrtvPonExtDeviceIndex,
				outBandInterfaceIP
					IpAddress,
				outBandInterfaceMask
					IpAddress,
				outBandInterfaceEnable
					TruthValue,
				outBandInterfaceDesc
					OCTET STRING,
				outBandInterfaceGateway
					IpAddress,
				outBandInterfaceLinkStatus
					INTEGER
			 }

		-- 1.3.6.1.4.1.34592.1.3.100.1.2.2.1.1
		outBandInterfaceDeviceIndex OBJECT-TYPE
			SYNTAX NscrtvPonExtDeviceIndex
			MAX-ACCESS not-accessible
			STATUS current
			DESCRIPTION
				"带外管理接口.
				
				带外管理IP配置表定义"
			::= { outBandInterfaceEntry 1 }

		
		-- 1.3.6.1.4.1.34592.1.3.100.1.2.2.1.2
		outBandInterfaceIP OBJECT-TYPE
			SYNTAX IpAddress
			MAX-ACCESS read-write
			STATUS current
			DESCRIPTION
				"
				带外管理接口IP地址"
			::= { outBandInterfaceEntry 2 }

		
		-- 1.3.6.1.4.1.34592.1.3.100.1.2.2.1.3
		outBandInterfaceMask OBJECT-TYPE
			SYNTAX IpAddress
			MAX-ACCESS read-write
			STATUS current
			DESCRIPTION
				"
				带外管理接口IP掩码"
			::= { outBandInterfaceEntry 3 }

		
		-- 1.3.6.1.4.1.34592.1.3.100.1.2.2.1.4
		outBandInterfaceEnable OBJECT-TYPE
			SYNTAX TruthValue
			MAX-ACCESS read-write
			STATUS current
			DESCRIPTION
				"
				带外管理接口开关"
			::= { outBandInterfaceEntry 4 }

		
		-- 1.3.6.1.4.1.34592.1.3.100.1.2.2.1.5
		outBandInterfaceDesc OBJECT-TYPE
			SYNTAX OCTET STRING
			MAX-ACCESS read-write
			STATUS current
			DESCRIPTION
				" Description "
			::= { outBandInterfaceEntry 5 }

		
		-- 1.3.6.1.4.1.34592.1.3.100.1.2.2.1.6
		outBandInterfaceGateway OBJECT-TYPE
			SYNTAX IpAddress
			MAX-ACCESS read-write
			STATUS current
			DESCRIPTION
				"带外管理接口默认网关"
			::= { outBandInterfaceEntry 6 }

		
		-- 1.3.6.1.4.1.34592.1.3.100.1.2.2.1.7
		outBandInterfaceLinkStatus OBJECT-TYPE
			SYNTAX INTEGER
				{
				up(1),
				down(2)
				}
			MAX-ACCESS read-only
			STATUS current
			DESCRIPTION
				"Description."
			::= { outBandInterfaceEntry 7 }

		
		-- 1.3.6.1.4.1.34592.1.3.100.1.2.3
		inBandInterfaceIpv6Table OBJECT-TYPE
			SYNTAX SEQUENCE OF InBandInterfaceIpv6Entry
			MAX-ACCESS not-accessible
			STATUS current
			DESCRIPTION
				"Description."
			::= { interfaceManagementObjects 3 }

		
		-- 1.3.6.1.4.1.34592.1.3.100.1.2.3.1
		inBandInterfaceIpv6Entry OBJECT-TYPE
			SYNTAX InBandInterfaceIpv6Entry
			MAX-ACCESS not-accessible
			STATUS current
			DESCRIPTION
				"Description."
			INDEX { inBandInterfaceVlanIdIndex, inBandInterfaceIpv6Index }
			::= { inBandInterfaceIpv6Table 1 }

		
		InBandInterfaceIpv6Entry ::=
			SEQUENCE { 
				inBandInterfaceIpv6Index
					INTEGER,
				inBandInterfaceIpv6addr
					Ipv6Address,
				inBandInterfaceIpv6Prefix
					Integer32,
				inBandInterfaceIpv6RowStatus
					RowStatus
			 }

		-- 1.3.6.1.4.1.34592.1.3.100.1.2.3.1.1
		inBandInterfaceIpv6Index OBJECT-TYPE
			SYNTAX INTEGER
			MAX-ACCESS not-accessible
			STATUS current
			DESCRIPTION
				"Description."
			::= { inBandInterfaceIpv6Entry 1 }

		
		-- 1.3.6.1.4.1.34592.1.3.100.1.2.3.1.2
		inBandInterfaceIpv6addr OBJECT-TYPE
			SYNTAX Ipv6Address
			MAX-ACCESS read-create
			STATUS current
			DESCRIPTION
				"Description."
			::= { inBandInterfaceIpv6Entry 2 }

		
		-- 1.3.6.1.4.1.34592.1.3.100.1.2.3.1.3
		inBandInterfaceIpv6Prefix OBJECT-TYPE
			SYNTAX Integer32 (1..128)
			MAX-ACCESS read-create
			STATUS current
			DESCRIPTION
				"Description."
			::= { inBandInterfaceIpv6Entry 3 }

		
		-- 1.3.6.1.4.1.34592.1.3.100.1.2.3.1.4
		inBandInterfaceIpv6RowStatus OBJECT-TYPE
			SYNTAX RowStatus
			MAX-ACCESS read-create
			STATUS current
			DESCRIPTION
				"Description."
			::= { inBandInterfaceIpv6Entry 4 }

		
		-- 1.3.6.1.4.1.34592.1.3.100.1.2.4
		outBandInterfaceIpv6Table OBJECT-TYPE
			SYNTAX SEQUENCE OF OutBandInterfaceIpv6Entry
			MAX-ACCESS not-accessible
			STATUS current
			DESCRIPTION
				"Description."
			::= { interfaceManagementObjects 4 }

		
		-- 1.3.6.1.4.1.34592.1.3.100.1.2.4.1
		outBandInterfaceIpv6Entry OBJECT-TYPE
			SYNTAX OutBandInterfaceIpv6Entry
			MAX-ACCESS not-accessible
			STATUS current
			DESCRIPTION
				"Description."
			INDEX { outBandInterfaceIpv6Index }
			::= { outBandInterfaceIpv6Table 1 }

		
		OutBandInterfaceIpv6Entry ::=
			SEQUENCE { 
				outBandInterfaceIpv6Index
					INTEGER,
				outBandInterfaceIpv6addr
					Ipv6Address,
				outBandInterfaceIpv6Prefix
					Integer32,
				outBandInterfaceIpv6RowStatus
					RowStatus
			 }

		-- 1.3.6.1.4.1.34592.1.3.100.1.2.4.1.1
		outBandInterfaceIpv6Index OBJECT-TYPE
			SYNTAX INTEGER
			MAX-ACCESS not-accessible
			STATUS current
			DESCRIPTION
				"Description."
			::= { outBandInterfaceIpv6Entry 1 }

		
		-- 1.3.6.1.4.1.34592.1.3.100.1.2.4.1.2
		outBandInterfaceIpv6addr OBJECT-TYPE
			SYNTAX Ipv6Address
			MAX-ACCESS read-create
			STATUS current
			DESCRIPTION
				"Description."
			::= { outBandInterfaceIpv6Entry 2 }

		
		-- 1.3.6.1.4.1.34592.1.3.100.1.2.4.1.3
		outBandInterfaceIpv6Prefix OBJECT-TYPE
			SYNTAX Integer32 (1..128)
			MAX-ACCESS read-create
			STATUS current
			DESCRIPTION
				"Description."
			::= { outBandInterfaceIpv6Entry 3 }

		
		-- 1.3.6.1.4.1.34592.1.3.100.1.2.4.1.4
		outBandInterfaceIpv6RowStatus OBJECT-TYPE
			SYNTAX RowStatus
			MAX-ACCESS read-create
			STATUS current
			DESCRIPTION
				"Description."
			::= { outBandInterfaceIpv6Entry 4 }

		
		-- 1.3.6.1.4.1.34592.1.3.100.1.2.5
		dnsServerTable OBJECT-TYPE
			SYNTAX SEQUENCE OF DnsServerEntry
			MAX-ACCESS not-accessible
			STATUS current
			DESCRIPTION
				"Description."
			::= { interfaceManagementObjects 5 }

		
		-- 1.3.6.1.4.1.34592.1.3.100.1.2.5.1
		dnsServerEntry OBJECT-TYPE
			SYNTAX DnsServerEntry
			MAX-ACCESS not-accessible
			STATUS current
			DESCRIPTION
				"Description."
			INDEX { dnsServerIndex }
			::= { dnsServerTable 1 }

		
		DnsServerEntry ::=
			SEQUENCE { 
				dnsServerIndex
					INTEGER,
				dnsServerIp
					IpAddress,
				dnsServerIpRowStatus
					RowStatus
			 }

		-- 1.3.6.1.4.1.34592.1.3.100.1.2.5.1.1
		dnsServerIndex OBJECT-TYPE
			SYNTAX INTEGER (0..1)
			MAX-ACCESS not-accessible
			STATUS current
			DESCRIPTION
				"Description."
			::= { dnsServerEntry 1 }

		
		-- 1.3.6.1.4.1.34592.1.3.100.1.2.5.1.2
		dnsServerIp OBJECT-TYPE
			SYNTAX IpAddress
			MAX-ACCESS read-create
			STATUS current
			DESCRIPTION
				"Description."
			::= { dnsServerEntry 2 }

		
		-- 1.3.6.1.4.1.34592.1.3.100.1.2.5.1.3
		dnsServerIpRowStatus OBJECT-TYPE
			SYNTAX RowStatus
			MAX-ACCESS read-create
			STATUS current
			DESCRIPTION
				"Description."
			::= { dnsServerEntry 3 }

		
		-- 1.3.6.1.4.1.34592.1.3.100.1.3
		syslogConfigObjects OBJECT IDENTIFIER ::= { systemObjects 3 }

		
		-- 1.3.6.1.4.1.34592.1.3.100.1.3.1
		syslogConfigOperLogEnable OBJECT-TYPE
			SYNTAX TruthValue
			MAX-ACCESS read-write
			STATUS current
			DESCRIPTION
				"Description."
			::= { syslogConfigObjects 1 }

		
		-- 1.3.6.1.4.1.34592.1.3.100.1.3.2
		syslogConfigAlarmLogEnable OBJECT-TYPE
			SYNTAX TruthValue
			MAX-ACCESS read-write
			STATUS current
			DESCRIPTION
				"Description."
			::= { syslogConfigObjects 2 }

		
		-- 1.3.6.1.4.1.34592.1.3.100.1.3.3
		syslogConfigTable OBJECT-TYPE
			SYNTAX SEQUENCE OF SyslogConfigEntry
			MAX-ACCESS not-accessible
			STATUS current
			DESCRIPTION
				"Description."
			::= { syslogConfigObjects 3 }

		
		-- 1.3.6.1.4.1.34592.1.3.100.1.3.3.1
		syslogConfigEntry OBJECT-TYPE
			SYNTAX SyslogConfigEntry
			MAX-ACCESS not-accessible
			STATUS current
			DESCRIPTION
				"Description."
			INDEX { syslogIndex }
			::= { syslogConfigTable 1 }

		
		SyslogConfigEntry ::=
			SEQUENCE { 
				syslogIndex
					INTEGER,
				syslogServerIpaddress
					IpAddress,
				syslogConfigName
					OCTET STRING,
				syslogConfigActive
					TruthValue,
				syslogServerIpaddressRowStatus
					RowStatus,
				syslogConfigPort
					Unsigned32
			 }

		-- 1.3.6.1.4.1.34592.1.3.100.1.3.3.1.1
		syslogIndex OBJECT-TYPE
			SYNTAX INTEGER
			MAX-ACCESS read-write
			STATUS current
			DESCRIPTION
				"Description."
			::= { syslogConfigEntry 1 }

		
		-- 1.3.6.1.4.1.34592.1.3.100.1.3.3.1.2
		syslogServerIpaddress OBJECT-TYPE
			SYNTAX IpAddress
			MAX-ACCESS read-write
			STATUS current
			DESCRIPTION
				"Description."
			::= { syslogConfigEntry 2 }

		
		-- 1.3.6.1.4.1.34592.1.3.100.1.3.3.1.3
		syslogConfigName OBJECT-TYPE
			SYNTAX OCTET STRING
			MAX-ACCESS read-write
			STATUS current
			DESCRIPTION
				"Description."
			::= { syslogConfigEntry 3 }

		
		-- 1.3.6.1.4.1.34592.1.3.100.1.3.3.1.4
		syslogConfigActive OBJECT-TYPE
			SYNTAX TruthValue
			MAX-ACCESS read-write
			STATUS current
			DESCRIPTION
				"Description."
			::= { syslogConfigEntry 4 }

		
		-- 1.3.6.1.4.1.34592.1.3.100.1.3.3.1.5
		syslogServerIpaddressRowStatus OBJECT-TYPE
			SYNTAX RowStatus
			MAX-ACCESS read-create
			STATUS current
			DESCRIPTION
				"Description."
			::= { syslogConfigEntry 5 }

		
		-- 1.3.6.1.4.1.34592.1.3.100.1.3.3.1.6
		syslogConfigPort OBJECT-TYPE
			SYNTAX Unsigned32 (1..65535)
			MAX-ACCESS read-write
			STATUS current
			DESCRIPTION
				"Description."
			::= { syslogConfigEntry 6 }

		
		-- 1.3.6.1.4.1.34592.1.3.100.1.4
		alarmManagementObjects OBJECT IDENTIFIER ::= { systemObjects 4 }

		
		-- 1.3.6.1.4.1.34592.1.3.100.1.4.1
		alarmOutputDetailEnable OBJECT-TYPE
			SYNTAX TruthValue
			MAX-ACCESS read-write
			STATUS current
			DESCRIPTION
				"Description."
			::= { alarmManagementObjects 1 }

		
		-- 1.3.6.1.4.1.34592.1.3.100.1.4.2
		alarmOutputLimitEnable OBJECT-TYPE
			SYNTAX TruthValue
			MAX-ACCESS read-write
			STATUS current
			DESCRIPTION
				"Description."
			::= { alarmManagementObjects 2 }

		
		-- 1.3.6.1.4.1.34592.1.3.100.1.4.3
		alarmOutputLimit OBJECT-TYPE
			SYNTAX Integer32
			MAX-ACCESS read-write
			STATUS current
			DESCRIPTION
				"max alarm output counts period."
			::= { alarmManagementObjects 3 }

		
		-- 1.3.6.1.4.1.34592.1.3.100.1.4.4
		alarmJitterProofInterval OBJECT-TYPE
			SYNTAX Integer32
			MAX-ACCESS read-write
			STATUS current
			DESCRIPTION
				"time interval"
			::= { alarmManagementObjects 4 }

		
		-- 1.3.6.1.4.1.34592.1.3.100.1.4.5
		alarmJitterProof OBJECT-TYPE
			SYNTAX TruthValue
			MAX-ACCESS read-write
			STATUS current
			DESCRIPTION
				"enable or disable proof"
			::= { alarmManagementObjects 5 }

		
		-- 1.3.6.1.4.1.34592.1.3.100.1.4.6
		alarmIdConfigTable OBJECT-TYPE
			SYNTAX SEQUENCE OF AlarmIdConfigEntry
			MAX-ACCESS not-accessible
			STATUS current
			DESCRIPTION
				"Description."
			::= { alarmManagementObjects 6 }

		
		-- 1.3.6.1.4.1.34592.1.3.100.1.4.6.1
		alarmIdConfigEntry OBJECT-TYPE
			SYNTAX AlarmIdConfigEntry
			MAX-ACCESS not-accessible
			STATUS current
			DESCRIPTION
				"Description."
			INDEX { alarmId }
			::= { alarmIdConfigTable 1 }

		
		AlarmIdConfigEntry ::=
			SEQUENCE { 
				alarmId
					Unsigned32,
				alarmIdLevel
					Integer32,
				alarmIdOuputEnable
					TruthValue,
				alarmIdTrapEnable
					TruthValue,
				alarmIdRecordEnable
					TruthValue,
				alarmIdRemoteEnable
					TruthValue
			 }

		-- 1.3.6.1.4.1.34592.1.3.100.1.4.6.1.1
		alarmId OBJECT-TYPE
			SYNTAX Unsigned32
			MAX-ACCESS read-write
			STATUS current
			DESCRIPTION
				"Description."
			::= { alarmIdConfigEntry 1 }

		
		-- 1.3.6.1.4.1.34592.1.3.100.1.4.6.1.2
		alarmIdLevel OBJECT-TYPE
			SYNTAX Integer32
			MAX-ACCESS read-write
			STATUS current
			DESCRIPTION
				"Description."
			::= { alarmIdConfigEntry 2 }

		
		-- 1.3.6.1.4.1.34592.1.3.100.1.4.6.1.3
		alarmIdOuputEnable OBJECT-TYPE
			SYNTAX TruthValue
			MAX-ACCESS read-write
			STATUS current
			DESCRIPTION
				"Description."
			::= { alarmIdConfigEntry 3 }

		
		-- 1.3.6.1.4.1.34592.1.3.100.1.4.6.1.4
		alarmIdTrapEnable OBJECT-TYPE
			SYNTAX TruthValue
			MAX-ACCESS read-write
			STATUS current
			DESCRIPTION
				"Description."
			::= { alarmIdConfigEntry 4 }

		
		-- 1.3.6.1.4.1.34592.1.3.100.1.4.6.1.5
		alarmIdRecordEnable OBJECT-TYPE
			SYNTAX TruthValue
			MAX-ACCESS read-write
			STATUS current
			DESCRIPTION
				"Description."
			::= { alarmIdConfigEntry 5 }

		
		-- 1.3.6.1.4.1.34592.1.3.100.1.4.6.1.6
		alarmIdRemoteEnable OBJECT-TYPE
			SYNTAX TruthValue
			MAX-ACCESS read-write
			STATUS current
			DESCRIPTION
				"Description."
			::= { alarmIdConfigEntry 6 }

		
		-- 1.3.6.1.4.1.34592.1.3.100.1.5
		eventManagementObjects OBJECT IDENTIFIER ::= { systemObjects 5 }

		
		-- 1.3.6.1.4.1.34592.1.3.100.1.5.1
		eventOutputDetailEnable OBJECT-TYPE
			SYNTAX TruthValue
			MAX-ACCESS read-write
			STATUS current
			DESCRIPTION
				"Description."
			::= { eventManagementObjects 1 }

		
		-- 1.3.6.1.4.1.34592.1.3.100.1.5.2
		eventConfigTable OBJECT-TYPE
			SYNTAX SEQUENCE OF EventConfigEntry
			MAX-ACCESS not-accessible
			STATUS current
			DESCRIPTION
				"Description."
			::= { eventManagementObjects 2 }

		
		-- 1.3.6.1.4.1.34592.1.3.100.1.5.2.1
		eventConfigEntry OBJECT-TYPE
			SYNTAX EventConfigEntry
			MAX-ACCESS not-accessible
			STATUS current
			DESCRIPTION
				"Description."
			INDEX { eventId }
			::= { eventConfigTable 1 }

		
		EventConfigEntry ::=
			SEQUENCE { 
				eventId
					Integer32,
				eventIdLevel
					Integer32,
				eventIdOutPutEnable
					TruthValue,
				eventIdTrapEnable
					TruthValue,
				eventIdRecordEnable
					TruthValue,
				eventIdRemoteEnable
					TruthValue
			 }

		-- 1.3.6.1.4.1.34592.1.3.100.1.5.2.1.1
		eventId OBJECT-TYPE
			SYNTAX Integer32
			MAX-ACCESS read-write
			STATUS current
			DESCRIPTION
				"Description."
			::= { eventConfigEntry 1 }

		
		-- 1.3.6.1.4.1.34592.1.3.100.1.5.2.1.2
		eventIdLevel OBJECT-TYPE
			SYNTAX Integer32
			MAX-ACCESS read-write
			STATUS current
			DESCRIPTION
				"Description."
			::= { eventConfigEntry 2 }

		
		-- 1.3.6.1.4.1.34592.1.3.100.1.5.2.1.3
		eventIdOutPutEnable OBJECT-TYPE
			SYNTAX TruthValue
			MAX-ACCESS read-write
			STATUS current
			DESCRIPTION
				"Description."
			::= { eventConfigEntry 3 }

		
		-- 1.3.6.1.4.1.34592.1.3.100.1.5.2.1.4
		eventIdTrapEnable OBJECT-TYPE
			SYNTAX TruthValue
			MAX-ACCESS read-write
			STATUS current
			DESCRIPTION
				"Description."
			::= { eventConfigEntry 4 }

		
		-- 1.3.6.1.4.1.34592.1.3.100.1.5.2.1.5
		eventIdRecordEnable OBJECT-TYPE
			SYNTAX TruthValue
			MAX-ACCESS read-write
			STATUS current
			DESCRIPTION
				"Description."
			::= { eventConfigEntry 5 }

		
		-- 1.3.6.1.4.1.34592.1.3.100.1.5.2.1.6
		eventIdRemoteEnable OBJECT-TYPE
			SYNTAX TruthValue
			MAX-ACCESS read-write
			STATUS current
			DESCRIPTION
				"Description."
			::= { eventConfigEntry 6 }

		
		-- 1.3.6.1.4.1.34592.1.3.100.1.6
		serviceManageObjects OBJECT IDENTIFIER ::= { systemObjects 6 }

		
		-- 1.3.6.1.4.1.34592.1.3.100.1.6.1
		serviceDefaultAction OBJECT-TYPE
			SYNTAX TruthValue
				{
				permit(0),
				deny(1)
				}
			MAX-ACCESS read-write
			STATUS current
			DESCRIPTION
				"The default action for the packet to access the device."
			::= { serviceManageObjects 1 }

		
		-- 1.3.6.1.4.1.34592.1.3.100.1.6.2
		serviceTelnetRuleTable OBJECT-TYPE
			SYNTAX SEQUENCE OF ServiceTelnetRuleEntry
			MAX-ACCESS not-accessible
			STATUS current
			DESCRIPTION
				"Description."
			::= { serviceManageObjects 2 }

		
		-- 1.3.6.1.4.1.34592.1.3.100.1.6.2.1
		serviceTelnetRuleEntry OBJECT-TYPE
			SYNTAX ServiceTelnetRuleEntry
			MAX-ACCESS not-accessible
			STATUS current
			DESCRIPTION
				"Description."
			INDEX { serviceTelnetRuleIndex }
			::= { serviceTelnetRuleTable 1 }

		
		ServiceTelnetRuleEntry ::=
			SEQUENCE { 
				serviceTelnetRuleIndex
					Integer32,
				serviceTelnetRuleRealIndex
					Integer32,
				serviceTelnetRuleStartIP
					IpAddress,
				serviceTelnetRuleEndIP
					IpAddress,
				serviceTelnetRuleAction
					TruthValue,
				serviceTelnetRuleRowStatus
					RowStatus
			 }

		-- 1.3.6.1.4.1.34592.1.3.100.1.6.2.1.1
		serviceTelnetRuleIndex OBJECT-TYPE
			SYNTAX Integer32
			MAX-ACCESS not-accessible
			STATUS current
			DESCRIPTION
				"Index of the telnet service rule for packet to access the device"
			::= { serviceTelnetRuleEntry 1 }

		
		-- 1.3.6.1.4.1.34592.1.3.100.1.6.2.1.2
		serviceTelnetRuleRealIndex OBJECT-TYPE
			SYNTAX Integer32
			MAX-ACCESS read-only
			STATUS current
			DESCRIPTION
				"Description."
			::= { serviceTelnetRuleEntry 2 }

		
		-- 1.3.6.1.4.1.34592.1.3.100.1.6.2.1.3
		serviceTelnetRuleStartIP OBJECT-TYPE
			SYNTAX IpAddress
			MAX-ACCESS read-write
			STATUS current
			DESCRIPTION
				"StartIP of the telnet service rule for packet to access the device"
			::= { serviceTelnetRuleEntry 3 }

		
		-- 1.3.6.1.4.1.34592.1.3.100.1.6.2.1.4
		serviceTelnetRuleEndIP OBJECT-TYPE
			SYNTAX IpAddress
			MAX-ACCESS read-write
			STATUS current
			DESCRIPTION
				"EndIP of the telnet service rule for packet to access the device"
			::= { serviceTelnetRuleEntry 4 }

		
		-- 1.3.6.1.4.1.34592.1.3.100.1.6.2.1.5
		serviceTelnetRuleAction OBJECT-TYPE
			SYNTAX TruthValue
				{
				permit(0),
				deny(1)
				}
			MAX-ACCESS read-write
			STATUS current
			DESCRIPTION
				"The action of the rule for packet to telnet the device."
			::= { serviceTelnetRuleEntry 5 }

		
		-- 1.3.6.1.4.1.34592.1.3.100.1.6.2.1.6
		serviceTelnetRuleRowStatus OBJECT-TYPE
			SYNTAX RowStatus
			MAX-ACCESS read-create
			STATUS current
			DESCRIPTION
				"Description."
			::= { serviceTelnetRuleEntry 6 }

		
		-- 1.3.6.1.4.1.34592.1.3.100.1.6.3
		serviceHttpRuleTable OBJECT-TYPE
			SYNTAX SEQUENCE OF ServiceHttpRuleEntry
			MAX-ACCESS not-accessible
			STATUS current
			DESCRIPTION
				"Description."
			::= { serviceManageObjects 3 }

		
		-- 1.3.6.1.4.1.34592.1.3.100.1.6.3.1
		serviceHttpRuleEntry OBJECT-TYPE
			SYNTAX ServiceHttpRuleEntry
			MAX-ACCESS not-accessible
			STATUS current
			DESCRIPTION
				"Description."
			INDEX { serviceHttpRuleIndex }
			::= { serviceHttpRuleTable 1 }

		
		ServiceHttpRuleEntry ::=
			SEQUENCE { 
				serviceHttpRuleIndex
					Integer32,
				serviceHttpRuleRealIndex
					Integer32,
				serviceHttpRuleStartIP
					IpAddress,
				serviceHttpRuleEndIP
					IpAddress,
				serviceHttpRuleAction
					TruthValue,
				serviceHttpRuleRowStatus
					RowStatus
			 }

		-- 1.3.6.1.4.1.34592.1.3.100.1.6.3.1.1
		serviceHttpRuleIndex OBJECT-TYPE
			SYNTAX Integer32
			MAX-ACCESS not-accessible
			STATUS current
			DESCRIPTION
				"Index of the http service rule for packet to access the device"
			::= { serviceHttpRuleEntry 1 }

		
		-- 1.3.6.1.4.1.34592.1.3.100.1.6.3.1.2
		serviceHttpRuleRealIndex OBJECT-TYPE
			SYNTAX Integer32
			MAX-ACCESS read-only
			STATUS current
			DESCRIPTION
				"Description."
			::= { serviceHttpRuleEntry 2 }

		
		-- 1.3.6.1.4.1.34592.1.3.100.1.6.3.1.3
		serviceHttpRuleStartIP OBJECT-TYPE
			SYNTAX IpAddress
			MAX-ACCESS read-write
			STATUS current
			DESCRIPTION
				"StartIP of the http service rule for packet to access the device"
			::= { serviceHttpRuleEntry 3 }

		
		-- 1.3.6.1.4.1.34592.1.3.100.1.6.3.1.4
		serviceHttpRuleEndIP OBJECT-TYPE
			SYNTAX IpAddress
			MAX-ACCESS read-write
			STATUS current
			DESCRIPTION
				"EndIP of the http service rule for packet to access the device"
			::= { serviceHttpRuleEntry 4 }

		
		-- 1.3.6.1.4.1.34592.1.3.100.1.6.3.1.5
		serviceHttpRuleAction OBJECT-TYPE
			SYNTAX TruthValue
				{
				permit(0),
				deny(1)
				}
			MAX-ACCESS read-write
			STATUS current
			DESCRIPTION
				"The action of the rule for packet to http the device."
			::= { serviceHttpRuleEntry 5 }

		
		-- 1.3.6.1.4.1.34592.1.3.100.1.6.3.1.6
		serviceHttpRuleRowStatus OBJECT-TYPE
			SYNTAX RowStatus
			MAX-ACCESS read-create
			STATUS current
			DESCRIPTION
				"Description."
			::= { serviceHttpRuleEntry 6 }

		
		-- 1.3.6.1.4.1.34592.1.3.100.1.6.4
		serviceSshRuleTable OBJECT-TYPE
			SYNTAX SEQUENCE OF ServiceSshRuleEntry
			MAX-ACCESS not-accessible
			STATUS current
			DESCRIPTION
				"Description."
			::= { serviceManageObjects 4 }

		
		-- 1.3.6.1.4.1.34592.1.3.100.1.6.4.1
		serviceSshRuleEntry OBJECT-TYPE
			SYNTAX ServiceSshRuleEntry
			MAX-ACCESS not-accessible
			STATUS current
			DESCRIPTION
				"Description."
			INDEX { serviceSshRuleIndex }
			::= { serviceSshRuleTable 1 }

		
		ServiceSshRuleEntry ::=
			SEQUENCE { 
				serviceSshRuleIndex
					Integer32,
				serviceSshRuleRealIndex
					Integer32,
				serviceSshRuleStartIP
					IpAddress,
				serviceSshRuleEndIP
					IpAddress,
				serviceSshRuleAction
					TruthValue,
				serviceSshRuleRowStatus
					RowStatus
			 }

		-- 1.3.6.1.4.1.34592.1.3.100.1.6.4.1.1
		serviceSshRuleIndex OBJECT-TYPE
			SYNTAX Integer32
			MAX-ACCESS not-accessible
			STATUS current
			DESCRIPTION
				"Index of the ssh service rule for packet to access the device"
			::= { serviceSshRuleEntry 1 }

		
		-- 1.3.6.1.4.1.34592.1.3.100.1.6.4.1.2
		serviceSshRuleRealIndex OBJECT-TYPE
			SYNTAX Integer32
			MAX-ACCESS read-only
			STATUS current
			DESCRIPTION
				"Description."
			::= { serviceSshRuleEntry 2 }

		
		-- 1.3.6.1.4.1.34592.1.3.100.1.6.4.1.3
		serviceSshRuleStartIP OBJECT-TYPE
			SYNTAX IpAddress
			MAX-ACCESS read-write
			STATUS current
			DESCRIPTION
				"StartIP of the ssh service rule for packet to access the device"
			::= { serviceSshRuleEntry 3 }

		
		-- 1.3.6.1.4.1.34592.1.3.100.1.6.4.1.4
		serviceSshRuleEndIP OBJECT-TYPE
			SYNTAX IpAddress
			MAX-ACCESS read-write
			STATUS current
			DESCRIPTION
				"EndIP of the ssh service rule for packet to access the device"
			::= { serviceSshRuleEntry 4 }

		
		-- 1.3.6.1.4.1.34592.1.3.100.1.6.4.1.5
		serviceSshRuleAction OBJECT-TYPE
			SYNTAX TruthValue
				{
				permit(0),
				deny(1)
				}
			MAX-ACCESS read-write
			STATUS current
			DESCRIPTION
				"The action of the rule for packet to ssh the device."
			::= { serviceSshRuleEntry 5 }

		
		-- 1.3.6.1.4.1.34592.1.3.100.1.6.4.1.6
		serviceSshRuleRowStatus OBJECT-TYPE
			SYNTAX RowStatus
			MAX-ACCESS read-create
			STATUS current
			DESCRIPTION
				"Description."
			::= { serviceSshRuleEntry 6 }

		
		-- 1.3.6.1.4.1.34592.1.3.100.1.6.5
		serviceSnmpRuleTable OBJECT-TYPE
			SYNTAX SEQUENCE OF ServiceSnmpRuleEntry
			MAX-ACCESS not-accessible
			STATUS current
			DESCRIPTION
				"Description."
			::= { serviceManageObjects 5 }

		
		-- 1.3.6.1.4.1.34592.1.3.100.1.6.5.1
		serviceSnmpRuleEntry OBJECT-TYPE
			SYNTAX ServiceSnmpRuleEntry
			MAX-ACCESS not-accessible
			STATUS current
			DESCRIPTION
				"Description."
			INDEX { serviceSnmpRuleIndex }
			::= { serviceSnmpRuleTable 1 }

		
		ServiceSnmpRuleEntry ::=
			SEQUENCE { 
				serviceSnmpRuleIndex
					Integer32,
				serviceSnmpRuleRealIndex
					Integer32,
				serviceSnmpRuleStartIP
					IpAddress,
				serviceSnmpRuleEndIP
					IpAddress,
				serviceSnmpRuleAction
					TruthValue,
				serviceSnmpRuleRowStatus
					RowStatus
			 }

		-- 1.3.6.1.4.1.34592.1.3.100.1.6.5.1.1
		serviceSnmpRuleIndex OBJECT-TYPE
			SYNTAX Integer32
			MAX-ACCESS not-accessible
			STATUS current
			DESCRIPTION
				"Index of the snmp service rule for packet to access the device"
			::= { serviceSnmpRuleEntry 1 }

		
		-- 1.3.6.1.4.1.34592.1.3.100.1.6.5.1.2
		serviceSnmpRuleRealIndex OBJECT-TYPE
			SYNTAX Integer32
			MAX-ACCESS read-only
			STATUS current
			DESCRIPTION
				"Description."
			::= { serviceSnmpRuleEntry 2 }

		
		-- 1.3.6.1.4.1.34592.1.3.100.1.6.5.1.3
		serviceSnmpRuleStartIP OBJECT-TYPE
			SYNTAX IpAddress
			MAX-ACCESS read-write
			STATUS current
			DESCRIPTION
				"StartIP of the snmp service rule for packet to access the device"
			::= { serviceSnmpRuleEntry 3 }

		
		-- 1.3.6.1.4.1.34592.1.3.100.1.6.5.1.4
		serviceSnmpRuleEndIP OBJECT-TYPE
			SYNTAX IpAddress
			MAX-ACCESS read-write
			STATUS current
			DESCRIPTION
				"EndIP of the snmp service rule for packet to access the device"
			::= { serviceSnmpRuleEntry 4 }

		
		-- 1.3.6.1.4.1.34592.1.3.100.1.6.5.1.5
		serviceSnmpRuleAction OBJECT-TYPE
			SYNTAX TruthValue
				{
				permit(0),
				deny(1)
				}
			MAX-ACCESS read-write
			STATUS current
			DESCRIPTION
				"The action of the rule for packet to snmp the device."
			::= { serviceSnmpRuleEntry 5 }

		
		-- 1.3.6.1.4.1.34592.1.3.100.1.6.5.1.6
		serviceSnmpRuleRowStatus OBJECT-TYPE
			SYNTAX RowStatus
			MAX-ACCESS read-create
			STATUS current
			DESCRIPTION
				"Description."
			::= { serviceSnmpRuleEntry 6 }

		
		-- 1.3.6.1.4.1.34592.1.3.100.1.6.6
		serviceHttpsRuleTable OBJECT-TYPE
			SYNTAX SEQUENCE OF ServiceHttpsRuleEntry
			MAX-ACCESS not-accessible
			STATUS current
			DESCRIPTION
				"Description."
			::= { serviceManageObjects 6 }

		
		-- 1.3.6.1.4.1.34592.1.3.100.1.6.6.1
		serviceHttpsRuleEntry OBJECT-TYPE
			SYNTAX ServiceHttpsRuleEntry
			MAX-ACCESS not-accessible
			STATUS current
			DESCRIPTION
				"Description."
			INDEX { serviceHttpsRuleIndex }
			::= { serviceHttpsRuleTable 1 }

		
		ServiceHttpsRuleEntry ::=
			SEQUENCE { 
				serviceHttpsRuleIndex
					Integer32,
				serviceHttpsRuleRealIndex
					Integer32,
				serviceHttpsRuleStartIP
					IpAddress,
				serviceHttpsRuleEndIP
					IpAddress,
				serviceHttpsRuleAction
					TruthValue,
				serviceHttpsRuleRowStatus
					RowStatus
			 }

		-- 1.3.6.1.4.1.34592.1.3.100.1.6.6.1.1
		serviceHttpsRuleIndex OBJECT-TYPE
			SYNTAX Integer32
			MAX-ACCESS not-accessible
			STATUS current
			DESCRIPTION
				"Index of the https service rule for packet to access the device"
			::= { serviceHttpsRuleEntry 1 }

		
		-- 1.3.6.1.4.1.34592.1.3.100.1.6.6.1.2
		serviceHttpsRuleRealIndex OBJECT-TYPE
			SYNTAX Integer32
			MAX-ACCESS read-only
			STATUS current
			DESCRIPTION
				"Description."
			::= { serviceHttpsRuleEntry 2 }

		
		-- 1.3.6.1.4.1.34592.1.3.100.1.6.6.1.3
		serviceHttpsRuleStartIP OBJECT-TYPE
			SYNTAX IpAddress
			MAX-ACCESS read-write
			STATUS current
			DESCRIPTION
				"StartIP of the https service rule for packet to access the device"
			::= { serviceHttpsRuleEntry 3 }

		
		-- 1.3.6.1.4.1.34592.1.3.100.1.6.6.1.4
		serviceHttpsRuleEndIP OBJECT-TYPE
			SYNTAX IpAddress
			MAX-ACCESS read-write
			STATUS current
			DESCRIPTION
				"EndIP of the https service rule for packet to access the device"
			::= { serviceHttpsRuleEntry 4 }

		
		-- 1.3.6.1.4.1.34592.1.3.100.1.6.6.1.5
		serviceHttpsRuleAction OBJECT-TYPE
			SYNTAX TruthValue
				{
				permit(0),
				deny(1)
				}
			MAX-ACCESS read-write
			STATUS current
			DESCRIPTION
				"The action of the rule for packet to https the device."
			::= { serviceHttpsRuleEntry 5 }

		
		-- 1.3.6.1.4.1.34592.1.3.100.1.6.6.1.6
		serviceHttpsRuleRowStatus OBJECT-TYPE
			SYNTAX RowStatus
			MAX-ACCESS read-create
			STATUS current
			DESCRIPTION
				"Description."
			::= { serviceHttpsRuleEntry 6 }

		
		-- 1.3.6.1.4.1.34592.1.3.100.1.6.7
		serviceConfigTable OBJECT-TYPE
			SYNTAX SEQUENCE OF ServiceConfigEntry
			MAX-ACCESS not-accessible
			STATUS current
			DESCRIPTION
				"Description."
			::= { serviceManageObjects 7 }

		
		-- 1.3.6.1.4.1.34592.1.3.100.1.6.7.1
		serviceConfigEntry OBJECT-TYPE
			SYNTAX ServiceConfigEntry
			MAX-ACCESS not-accessible
			STATUS current
			DESCRIPTION
				"Description."
			INDEX { serviceIndex }
			::= { serviceConfigTable 1 }

		
		ServiceConfigEntry ::=
			SEQUENCE { 
				serviceIndex
					Integer32,
				serviceName
					OCTET STRING,
				serviceConfigPort
					Unsigned32,
				serviceConfigStatus
					TruthValue
			 }

		-- 1.3.6.1.4.1.34592.1.3.100.1.6.7.1.1
		serviceIndex OBJECT-TYPE
			SYNTAX Integer32
			MAX-ACCESS not-accessible
			STATUS current
			DESCRIPTION
				"Description."
			::= { serviceConfigEntry 1 }

		
		-- 1.3.6.1.4.1.34592.1.3.100.1.6.7.1.2
		serviceName OBJECT-TYPE
			SYNTAX OCTET STRING
			MAX-ACCESS read-only
			STATUS current
			DESCRIPTION
				"Description."
			::= { serviceConfigEntry 2 }

		
		-- 1.3.6.1.4.1.34592.1.3.100.1.6.7.1.3
		serviceConfigPort OBJECT-TYPE
			SYNTAX Unsigned32 (1..65535)
			MAX-ACCESS read-write
			STATUS current
			DESCRIPTION
				"Description."
			::= { serviceConfigEntry 3 }

		
		-- 1.3.6.1.4.1.34592.1.3.100.1.6.7.1.4
		serviceConfigStatus OBJECT-TYPE
			SYNTAX TruthValue
			MAX-ACCESS read-write
			STATUS current
			DESCRIPTION
				"Description."
			::= { serviceConfigEntry 4 }

		
		-- 1.3.6.1.4.1.34592.1.3.100.1.7
		autoBackupManageObjects OBJECT IDENTIFIER ::= { systemObjects 7 }

		
		-- 1.3.6.1.4.1.34592.1.3.100.1.7.1
		autoBackupTable OBJECT-TYPE
			SYNTAX SEQUENCE OF AutoBackupEntry
			MAX-ACCESS not-accessible
			STATUS current
			DESCRIPTION
				"Description."
			::= { autoBackupManageObjects 1 }

		
		-- 1.3.6.1.4.1.34592.1.3.100.1.7.1.1
		autoBackupEntry OBJECT-TYPE
			SYNTAX AutoBackupEntry
			MAX-ACCESS not-accessible
			STATUS current
			DESCRIPTION
				"Description."
			INDEX { autoBackupIndex }
			::= { autoBackupTable 1 }

		
		AutoBackupEntry ::=
			SEQUENCE { 
				autoBackupIndex
					INTEGER,
				autoBackupFileType
					INTEGER,
				autoBackupTransferMode
					INTEGER,
				autoBackupIpAddress
					IpAddress,
				autoBackupFtpName
					OCTET STRING,
				autoBackupFtpPassword
					OCTET STRING,
				autoBackupIntervalDay
					INTEGER,
				autoBackupTime
					DisplayString,
				autoBackupLastStatus
					INTEGER,
				autoBackupSwitch
					TruthValue
			 }

		-- 1.3.6.1.4.1.34592.1.3.100.1.7.1.1.1
		autoBackupIndex OBJECT-TYPE
			SYNTAX INTEGER
			MAX-ACCESS read-only
			STATUS current
			DESCRIPTION
				"自动备份管理接口.
				自动备份配置表定义"
			::= { autoBackupEntry 1 }

		
		-- 1.3.6.1.4.1.34592.1.3.100.1.7.1.1.2
		autoBackupFileType OBJECT-TYPE
			SYNTAX INTEGER
				{
				configuration(1),
				alarm(2),
				log(3)
				}
			MAX-ACCESS read-only
			STATUS current
			DESCRIPTION
				"自动备份文件类型：
				1 configuration
				2 alarm
				3 log"
			::= { autoBackupEntry 2 }

		
		-- 1.3.6.1.4.1.34592.1.3.100.1.7.1.1.3
		autoBackupTransferMode OBJECT-TYPE
			SYNTAX INTEGER
				{
				ftp(1),
				tftp(2)
				}
			MAX-ACCESS read-write
			STATUS current
			DESCRIPTION
				"自动备份传输方式:
				1 ftp
				2 tftp"
			::= { autoBackupEntry 3 }

		
		-- 1.3.6.1.4.1.34592.1.3.100.1.7.1.1.4
		autoBackupIpAddress OBJECT-TYPE
			SYNTAX IpAddress
			MAX-ACCESS read-write
			STATUS current
			DESCRIPTION
				"自动备份服务器IP地址"
			::= { autoBackupEntry 4 }

		
		-- 1.3.6.1.4.1.34592.1.3.100.1.7.1.1.5
		autoBackupFtpName OBJECT-TYPE
			SYNTAX OCTET STRING (SIZE (0..31))
			MAX-ACCESS read-write
			STATUS current
			DESCRIPTION
				"自动备份FTP服务器用户名(1-31)"
			::= { autoBackupEntry 5 }

		
		-- 1.3.6.1.4.1.34592.1.3.100.1.7.1.1.6
		autoBackupFtpPassword OBJECT-TYPE
			SYNTAX OCTET STRING (SIZE (0..31))
			MAX-ACCESS read-write
			STATUS current
			DESCRIPTION
				"自动备份FTP服务器密码(1-31)"
			::= { autoBackupEntry 6 }

		
		-- 1.3.6.1.4.1.34592.1.3.100.1.7.1.1.7
		autoBackupIntervalDay OBJECT-TYPE
			SYNTAX INTEGER (1..10)
			MAX-ACCESS read-write
			STATUS current
			DESCRIPTION
				"自动备份间隔天数(1-10)"
			::= { autoBackupEntry 7 }

		
		-- 1.3.6.1.4.1.34592.1.3.100.1.7.1.1.8
		autoBackupTime OBJECT-TYPE
			SYNTAX DisplayString (SIZE (5))
			MAX-ACCESS read-write
			STATUS current
			DESCRIPTION
				"自动备份的时间
				Format: HH:MM"
			::= { autoBackupEntry 8 }

		
		-- 1.3.6.1.4.1.34592.1.3.100.1.7.1.1.9
		autoBackupLastStatus OBJECT-TYPE
			SYNTAX INTEGER
				{
				success(1),
				false(2),
				none(3)
				}
			MAX-ACCESS read-only
			STATUS current
			DESCRIPTION
				"上次自动备份的状态：
				1 success
				2 false
				3 none"
			::= { autoBackupEntry 9 }

		
		-- 1.3.6.1.4.1.34592.1.3.100.1.7.1.1.10
		autoBackupSwitch OBJECT-TYPE
			SYNTAX TruthValue
			MAX-ACCESS read-write
			STATUS current
			DESCRIPTION
				"自动备份开关：
				1 打开
				2 关闭"
			::= { autoBackupEntry 10 }

		
		-- 1.3.6.1.4.1.34592.1.3.100.1.8
		systemGlobalExtObjects OBJECT IDENTIFIER ::= { systemObjects 8 }

		
		-- 1.3.6.1.4.1.34592.1.3.100.1.8.1
		cpuUsage OBJECT-TYPE
			SYNTAX Integer32
			MAX-ACCESS read-only
			STATUS current
			DESCRIPTION
				"Description."
			::= { systemGlobalExtObjects 1 }

		
		-- 1.3.6.1.4.1.34592.1.3.100.1.8.2
		memTotalSize OBJECT-TYPE
			SYNTAX Integer32
			MAX-ACCESS read-only
			STATUS current
			DESCRIPTION
				"Description.(unit:MByte)"
			::= { systemGlobalExtObjects 2 }

		
		-- 1.3.6.1.4.1.34592.1.3.100.1.8.3
		memFreeSize OBJECT-TYPE
			SYNTAX Integer32
			MAX-ACCESS read-only
			STATUS current
			DESCRIPTION
				"Description.(unit:MByte)"
			::= { systemGlobalExtObjects 3 }

		
		-- 1.3.6.1.4.1.34592.1.3.100.1.8.4
		flashTotalSize OBJECT-TYPE
			SYNTAX Integer32
			MAX-ACCESS read-only
			STATUS current
			DESCRIPTION
				"Description.(unit:KByte)"
			::= { systemGlobalExtObjects 4 }

		
		-- 1.3.6.1.4.1.34592.1.3.100.1.8.5
		flashAvailableSize OBJECT-TYPE
			SYNTAX Integer32
			MAX-ACCESS read-only
			STATUS current
			DESCRIPTION
				"Description.(unit:KByte)"
			::= { systemGlobalExtObjects 5 }

		
		-- 1.3.6.1.4.1.34592.1.3.100.1.8.6
		temperature OBJECT-TYPE
			SYNTAX Integer32
			MAX-ACCESS read-only
			STATUS current
			DESCRIPTION
				"Description."
			::= { systemGlobalExtObjects 6 }

		
		-- 1.3.6.1.4.1.34592.1.3.100.1.8.7
		temperatureThreshold OBJECT-TYPE
			SYNTAX Integer32
			MAX-ACCESS read-write
			STATUS current
			DESCRIPTION
				"Description."
			::= { systemGlobalExtObjects 7 }

		
		-- 1.3.6.1.4.1.34592.1.3.100.1.8.8
		licenseRemainTimes OBJECT-TYPE
			SYNTAX Unsigned32
			MAX-ACCESS read-only
			STATUS current
			DESCRIPTION
				"Description."
			::= { systemGlobalExtObjects 8 }

		
		-- 1.3.6.1.4.1.34592.1.3.100.1.8.9
		licenseLimitTimes OBJECT-TYPE
			SYNTAX Unsigned32
			MAX-ACCESS read-only
			STATUS current
			DESCRIPTION
				"Description."
			::= { systemGlobalExtObjects 9 }

		
		-- 1.3.6.1.4.1.34592.1.3.100.1.8.10
		systemBootTime OBJECT-TYPE
			SYNTAX DateAndTime
			MAX-ACCESS read-only
			STATUS current
			DESCRIPTION
				"Description."
			::= { systemGlobalExtObjects 10 }

		
		-- 1.3.6.1.4.1.34592.1.3.100.1.8.11
		temperatureLowThreshold OBJECT-TYPE
			SYNTAX Integer32
			MAX-ACCESS read-write
			STATUS current
			DESCRIPTION
				"Description."
			::= { systemGlobalExtObjects 11 }

		
		-- 1.3.6.1.4.1.34592.1.3.100.1.8.12
		cpuUsageThreshold OBJECT-TYPE
			SYNTAX Integer32
			MAX-ACCESS read-write
			STATUS current
			DESCRIPTION
				"Description."
			::= { systemGlobalExtObjects 12 }

		
		-- 1.3.6.1.4.1.34592.1.3.100.1.8.13
		memUsageThreshold OBJECT-TYPE
			SYNTAX Integer32
			MAX-ACCESS read-write
			STATUS current
			DESCRIPTION
				"Description."
			::= { systemGlobalExtObjects 13 }

		
		-- 1.3.6.1.4.1.34592.1.3.100.1.8.14
		deviceHwinfo OBJECT-TYPE
			SYNTAX OCTET STRING
			MAX-ACCESS read-only
			STATUS current
			DESCRIPTION
				"Description."
			::= { systemGlobalExtObjects 14 }

		
		-- 1.3.6.1.4.1.34592.1.3.100.1.8.15
		deviceLicense OBJECT-TYPE
			SYNTAX OCTET STRING
			MAX-ACCESS read-write
			STATUS current
			DESCRIPTION
				"Description."
			::= { systemGlobalExtObjects 15 }

		
		-- 1.3.6.1.4.1.34592.1.3.100.1.8.16
		deviceFactoryReset OBJECT-TYPE
			SYNTAX TruthValue
			MAX-ACCESS read-write
			STATUS current
			DESCRIPTION
				"Description."
			::= { systemGlobalExtObjects 16 }

		
		-- 1.3.6.1.4.1.34592.1.3.100.1.9
		userManageObjects OBJECT IDENTIFIER ::= { systemObjects 9 }

		
		-- 1.3.6.1.4.1.34592.1.3.100.1.9.1
		userName OBJECT-TYPE
			SYNTAX OCTET STRING (SIZE (1..64))
			MAX-ACCESS read-write
			STATUS current
			DESCRIPTION
				"Description."
			::= { userManageObjects 1 }

		
		-- 1.3.6.1.4.1.34592.1.3.100.1.9.2
		password OBJECT-TYPE
			SYNTAX OCTET STRING (SIZE (1..16))
			MAX-ACCESS read-write
			STATUS current
			DESCRIPTION
				"Description."
			::= { userManageObjects 2 }

		
		-- 1.3.6.1.4.1.34592.1.3.100.1.9.3
		level OBJECT-TYPE
			SYNTAX Integer32
			MAX-ACCESS read-only
			STATUS current
			DESCRIPTION
				"Description."
			::= { userManageObjects 3 }

		
		-- 1.3.6.1.4.1.34592.1.3.100.1.9.4
		status OBJECT-TYPE
			SYNTAX Integer32
			MAX-ACCESS read-only
			STATUS current
			DESCRIPTION
				"Description."
			::= { userManageObjects 4 }

		
		-- 1.3.6.1.4.1.34592.1.3.100.1.9.5
		authMethod OBJECT-TYPE
			SYNTAX INTEGER
				{
				local(0),
				aaa(1),
				local-aaa(2)
				}
			MAX-ACCESS read-write
			STATUS current
			DESCRIPTION
				"Description."
			::= { userManageObjects 5 }

		
		-- 1.3.6.1.4.1.34592.1.3.100.1.9.6
		userManageTable OBJECT-TYPE
			SYNTAX SEQUENCE OF UserManageEntry
			MAX-ACCESS not-accessible
			STATUS current
			DESCRIPTION
				"Description."
			::= { userManageObjects 6 }

		
		-- 1.3.6.1.4.1.34592.1.3.100.1.9.6.1
		userManageEntry OBJECT-TYPE
			SYNTAX UserManageEntry
			MAX-ACCESS not-accessible
			STATUS current
			DESCRIPTION
				"Description."
			INDEX { userManageIndex }
			::= { userManageTable 1 }

		
		UserManageEntry ::=
			SEQUENCE { 
				userManageIndex
					Integer32,
				userManageName
					OCTET STRING,
				userManagePassword
					OCTET STRING,
				userManageGroup
					INTEGER,
				userManageRowStatus
					RowStatus
			 }

		-- 1.3.6.1.4.1.34592.1.3.100.1.9.6.1.1
		userManageIndex OBJECT-TYPE
			SYNTAX Integer32
			MAX-ACCESS not-accessible
			STATUS current
			DESCRIPTION
				"Description."
			::= { userManageEntry 1 }

		
		-- 1.3.6.1.4.1.34592.1.3.100.1.9.6.1.2
		userManageName OBJECT-TYPE
			SYNTAX OCTET STRING
			MAX-ACCESS read-write
			STATUS current
			DESCRIPTION
				"Description."
			::= { userManageEntry 2 }

		
		-- 1.3.6.1.4.1.34592.1.3.100.1.9.6.1.3
		userManagePassword OBJECT-TYPE
			SYNTAX OCTET STRING
			MAX-ACCESS read-write
			STATUS current
			DESCRIPTION
				"Description."
			::= { userManageEntry 3 }

		
		-- 1.3.6.1.4.1.34592.1.3.100.1.9.6.1.4
		userManageGroup OBJECT-TYPE
			SYNTAX INTEGER
				{
				guest(0),
				admin(1),
				root(2)
				}
			MAX-ACCESS read-write
			STATUS current
			DESCRIPTION
				"Description."
			::= { userManageEntry 4 }

		
		-- 1.3.6.1.4.1.34592.1.3.100.1.9.6.1.5
		userManageRowStatus OBJECT-TYPE
			SYNTAX RowStatus
			MAX-ACCESS read-create
			STATUS current
			DESCRIPTION
				"Description."
			::= { userManageEntry 5 }

		
		-- 1.3.6.1.4.1.34592.1.3.100.1.10
		backupConfigurationManageObjects OBJECT IDENTIFIER ::= { systemObjects 10 }

		
		-- 1.3.6.1.4.1.34592.1.3.100.1.10.1
		backupConfigurationTable OBJECT-TYPE
			SYNTAX SEQUENCE OF BackupConfigurationEntry
			MAX-ACCESS not-accessible
			STATUS current
			DESCRIPTION
				"Description."
			::= { backupConfigurationManageObjects 1 }

		
		-- 1.3.6.1.4.1.34592.1.3.100.1.10.1.1
		backupConfigurationEntry OBJECT-TYPE
			SYNTAX BackupConfigurationEntry
			MAX-ACCESS not-accessible
			STATUS current
			DESCRIPTION
				"Description."
			INDEX { backupConfigurationIndex }
			::= { backupConfigurationTable 1 }

		
		BackupConfigurationEntry ::=
			SEQUENCE { 
				backupConfigurationIndex
					INTEGER,
				backupConfigurationFormat
					INTEGER,
				backupConfigurationTransferMode
					INTEGER,
				backupConfigurationIpAddress
					IpAddress,
				backupConfigurationFtpName
					OCTET STRING,
				backupConfigurationFtpPassword
					OCTET STRING,
				backupConfigurationFileName
					OCTET STRING,
				backupConfigurationLastStatus
					INTEGER
			 }

		-- 1.3.6.1.4.1.34592.1.3.100.1.10.1.1.1
		backupConfigurationIndex OBJECT-TYPE
			SYNTAX INTEGER
			MAX-ACCESS read-only
			STATUS current
			DESCRIPTION
				"Description."
			::= { backupConfigurationEntry 1 }

		
		-- 1.3.6.1.4.1.34592.1.3.100.1.10.1.1.2
		backupConfigurationFormat OBJECT-TYPE
			SYNTAX INTEGER
				{
				gz(1),
				txt(2)
				}
			MAX-ACCESS read-write
			STATUS current
			DESCRIPTION
				"Description."
			::= { backupConfigurationEntry 2 }

		
		-- 1.3.6.1.4.1.34592.1.3.100.1.10.1.1.3
		backupConfigurationTransferMode OBJECT-TYPE
			SYNTAX INTEGER
				{
				ftp(1),
				tftp(2)
				}
			MAX-ACCESS read-write
			STATUS current
			DESCRIPTION
				"Description."
			::= { backupConfigurationEntry 3 }

		
		-- 1.3.6.1.4.1.34592.1.3.100.1.10.1.1.4
		backupConfigurationIpAddress OBJECT-TYPE
			SYNTAX IpAddress
			MAX-ACCESS read-write
			STATUS current
			DESCRIPTION
				"Description."
			::= { backupConfigurationEntry 4 }

		
		-- 1.3.6.1.4.1.34592.1.3.100.1.10.1.1.5
		backupConfigurationFtpName OBJECT-TYPE
			SYNTAX OCTET STRING (SIZE (1..32))
			MAX-ACCESS read-write
			STATUS current
			DESCRIPTION
				"Description."
			::= { backupConfigurationEntry 5 }

		
		-- 1.3.6.1.4.1.34592.1.3.100.1.10.1.1.6
		backupConfigurationFtpPassword OBJECT-TYPE
			SYNTAX OCTET STRING (SIZE (1..32))
			MAX-ACCESS read-write
			STATUS current
			DESCRIPTION
				"Description."
			::= { backupConfigurationEntry 6 }

		
		-- 1.3.6.1.4.1.34592.1.3.100.1.10.1.1.7
		backupConfigurationFileName OBJECT-TYPE
			SYNTAX OCTET STRING (SIZE (1..64))
			MAX-ACCESS read-write
			STATUS current
			DESCRIPTION
				"Description."
			::= { backupConfigurationEntry 7 }

		
		-- 1.3.6.1.4.1.34592.1.3.100.1.10.1.1.8
		backupConfigurationLastStatus OBJECT-TYPE
			SYNTAX INTEGER
				{
				success(1),
				false(2),
				none(3)
				}
			MAX-ACCESS read-only
			STATUS current
			DESCRIPTION
				"Description."
			::= { backupConfigurationEntry 8 }

		
		-- 1.3.6.1.4.1.34592.1.3.100.1.11
		ntpManageObjects OBJECT IDENTIFIER ::= { systemObjects 11 }

		
		-- 1.3.6.1.4.1.34592.1.3.100.1.11.1
		ntpServiceTable OBJECT-TYPE
			SYNTAX SEQUENCE OF NtpServiceEntry
			MAX-ACCESS not-accessible
			STATUS current
			DESCRIPTION
				"Description."
			::= { ntpManageObjects 1 }

		
		-- 1.3.6.1.4.1.34592.1.3.100.1.11.1.1
		ntpServiceEntry OBJECT-TYPE
			SYNTAX NtpServiceEntry
			MAX-ACCESS not-accessible
			STATUS current
			DESCRIPTION
				"Description."
			INDEX { ntpServiceDeviceIndex, ntpServiceIndex }
			::= { ntpServiceTable 1 }

		
		NtpServiceEntry ::=
			SEQUENCE { 
				ntpServiceDeviceIndex
					NscrtvPonExtDeviceIndex,
				ntpServiceIndex
					Unsigned32,
				ntpServiceSetIP
					IpAddress,
				ntpServiceSetDomainName
					OCTET STRING,
				ntpServiceStatusClockSource
					DisplayString,
				ntpServiceStatusStratum
					INTEGER,
				ntpServiceStatus
					DisplayString,
				ntpServiceStatusReferenceClockId
					DisplayString,
				ntpServiceStatusReach
					INTEGER,
				ntpServiceStatusCurrentPoll
					INTEGER,
				ntpServiceStatusNow
					INTEGER,
				ntpServiceStatusOffset
					DisplayString,
				ntpServiceStatusDelay
					DisplayString,
				ntpServiceStatusDisper
					DisplayString,
				ntpServiceRowStatus
					RowStatus,
				timeZoneInfo
					DisplayString
			 }

		-- 1.3.6.1.4.1.34592.1.3.100.1.11.1.1.1
		ntpServiceDeviceIndex OBJECT-TYPE
			SYNTAX NscrtvPonExtDeviceIndex
			MAX-ACCESS not-accessible
			STATUS current
			DESCRIPTION
				"ntpServiceDeviceIndex."
			::= { ntpServiceEntry 1 }

		
		-- 1.3.6.1.4.1.34592.1.3.100.1.11.1.1.2
		ntpServiceIndex OBJECT-TYPE
			SYNTAX Unsigned32 (1..9)
			MAX-ACCESS not-accessible
			STATUS current
			DESCRIPTION
				"ntpServiceIndex"
			::= { ntpServiceEntry 2 }

		
		-- 1.3.6.1.4.1.34592.1.3.100.1.11.1.1.3
		ntpServiceSetIP OBJECT-TYPE
			SYNTAX IpAddress
			MAX-ACCESS read-create
			STATUS current
			DESCRIPTION
				"When the table is created, only one of the ntpServiceSetIP and ntpServiceSetDomainName can be set, and modification is not supported after creation."
			::= { ntpServiceEntry 3 }

		
		-- 1.3.6.1.4.1.34592.1.3.100.1.11.1.1.4
		ntpServiceSetDomainName OBJECT-TYPE
			SYNTAX OCTET STRING (SIZE (4..64))
			MAX-ACCESS read-create
			STATUS current
			DESCRIPTION
				"When the table is created, only one of the ntpServiceSetIP and ntpServiceSetDomainName can be set, and modification is not supported after creation."
			::= { ntpServiceEntry 4 }

		
		-- 1.3.6.1.4.1.34592.1.3.100.1.11.1.1.5
		ntpServiceStatusClockSource OBJECT-TYPE
			SYNTAX DisplayString (SIZE (0..64))
			MAX-ACCESS read-only
			STATUS current
			DESCRIPTION
				"Ntp service clock source."
			::= { ntpServiceEntry 5 }

		
		-- 1.3.6.1.4.1.34592.1.3.100.1.11.1.1.6
		ntpServiceStatusStratum OBJECT-TYPE
			SYNTAX INTEGER
			MAX-ACCESS read-only
			STATUS current
			DESCRIPTION
				"Ntp service clock stratum."
			::= { ntpServiceEntry 6 }

		
		-- 1.3.6.1.4.1.34592.1.3.100.1.11.1.1.7
		ntpServiceStatus OBJECT-TYPE
			SYNTAX DisplayString (SIZE (0..64))
			MAX-ACCESS read-only
			STATUS current
			DESCRIPTION
				"Ntp service clock status."
			::= { ntpServiceEntry 7 }

		
		-- 1.3.6.1.4.1.34592.1.3.100.1.11.1.1.8
		ntpServiceStatusReferenceClockId OBJECT-TYPE
			SYNTAX DisplayString (SIZE (0..64))
			MAX-ACCESS read-only
			STATUS current
			DESCRIPTION
				"Ntp service reference clock ID."
			::= { ntpServiceEntry 8 }

		
		-- 1.3.6.1.4.1.34592.1.3.100.1.11.1.1.9
		ntpServiceStatusReach OBJECT-TYPE
			SYNTAX INTEGER
			MAX-ACCESS read-only
			STATUS current
			DESCRIPTION
				"Ntp service reach."
			::= { ntpServiceEntry 9 }

		
		-- 1.3.6.1.4.1.34592.1.3.100.1.11.1.1.10
		ntpServiceStatusCurrentPoll OBJECT-TYPE
			SYNTAX INTEGER
			MAX-ACCESS read-only
			STATUS current
			DESCRIPTION
				"Ntp service current poll."
			::= { ntpServiceEntry 10 }

		
		-- 1.3.6.1.4.1.34592.1.3.100.1.11.1.1.11
		ntpServiceStatusNow OBJECT-TYPE
			SYNTAX INTEGER
			MAX-ACCESS read-only
			STATUS current
			DESCRIPTION
				"Ntp service Now."
			::= { ntpServiceEntry 11 }

		
		-- 1.3.6.1.4.1.34592.1.3.100.1.11.1.1.12
		ntpServiceStatusOffset OBJECT-TYPE
			SYNTAX DisplayString (SIZE (0..64))
			MAX-ACCESS read-only
			STATUS current
			DESCRIPTION
				"Ntp service offset."
			::= { ntpServiceEntry 12 }

		
		-- 1.3.6.1.4.1.34592.1.3.100.1.11.1.1.13
		ntpServiceStatusDelay OBJECT-TYPE
			SYNTAX DisplayString (SIZE (0..64))
			MAX-ACCESS read-only
			STATUS current
			DESCRIPTION
				"Ntp service delay."
			::= { ntpServiceEntry 13 }

		
		-- 1.3.6.1.4.1.34592.1.3.100.1.11.1.1.14
		ntpServiceStatusDisper OBJECT-TYPE
			SYNTAX DisplayString (SIZE (0..64))
			MAX-ACCESS read-only
			STATUS current
			DESCRIPTION
				"Ntp service disper."
			::= { ntpServiceEntry 14 }

		
		-- 1.3.6.1.4.1.34592.1.3.100.1.11.1.1.15
		ntpServiceRowStatus OBJECT-TYPE
			SYNTAX RowStatus
			MAX-ACCESS read-create
			STATUS current
			DESCRIPTION
				" "
			::= { ntpServiceEntry 15 }

		
		-- 1.3.6.1.4.1.34592.1.3.100.1.11.1.1.20
		timeZoneInfo OBJECT-TYPE
			SYNTAX DisplayString
			MAX-ACCESS read-write
			STATUS current
			DESCRIPTION
				"Description."
			::= { ntpServiceEntry 20 }

		
		-- 1.3.6.1.4.1.34592.1.3.100.1.12
		snmpConfigObjects OBJECT IDENTIFIER ::= { systemObjects 12 }

		
		-- 1.3.6.1.4.1.34592.1.3.100.1.12.1
		snmpAgentCommunityTable OBJECT-TYPE
			SYNTAX SEQUENCE OF SnmpAgentCommunityEntry
			MAX-ACCESS not-accessible
			STATUS current
			DESCRIPTION
				"Description."
			::= { snmpConfigObjects 1 }

		
		-- 1.3.6.1.4.1.34592.1.3.100.1.12.1.1
		snmpAgentCommunityEntry OBJECT-TYPE
			SYNTAX SnmpAgentCommunityEntry
			MAX-ACCESS not-accessible
			STATUS current
			DESCRIPTION
				"Description."
			INDEX { snmpAgentCommunitIndex }
			::= { snmpAgentCommunityTable 1 }

		
		SnmpAgentCommunityEntry ::=
			SEQUENCE { 
				snmpAgentCommunitIndex
					Unsigned32,
				snmpAgentCommunityName
					OCTET STRING,
				snmpAgentCommunityAccessLevel
					INTEGER,
				snmpAgentCommunityRowStatus
					RowStatus
			 }

		-- 1.3.6.1.4.1.34592.1.3.100.1.12.1.1.1
		snmpAgentCommunitIndex OBJECT-TYPE
			SYNTAX Unsigned32
			MAX-ACCESS not-accessible
			STATUS current
			DESCRIPTION
				"Description."
			::= { snmpAgentCommunityEntry 1 }

		
		-- 1.3.6.1.4.1.34592.1.3.100.1.12.1.1.2
		snmpAgentCommunityName OBJECT-TYPE
			SYNTAX OCTET STRING (SIZE (1..32))
			MAX-ACCESS read-create
			STATUS current
			DESCRIPTION
				"Description."
			::= { snmpAgentCommunityEntry 2 }

		
		-- 1.3.6.1.4.1.34592.1.3.100.1.12.1.1.3
		snmpAgentCommunityAccessLevel OBJECT-TYPE
			SYNTAX INTEGER
				{
				invalid(0),
				read-only(1),
				read-write(2)
				}
			MAX-ACCESS read-create
			STATUS current
			DESCRIPTION
				"Description."
			::= { snmpAgentCommunityEntry 3 }

		
		-- 1.3.6.1.4.1.34592.1.3.100.1.12.1.1.4
		snmpAgentCommunityRowStatus OBJECT-TYPE
			SYNTAX RowStatus
			MAX-ACCESS read-create
			STATUS current
			DESCRIPTION
				"Description."
			::= { snmpAgentCommunityEntry 4 }

		
		-- 1.3.6.1.4.1.34592.1.3.100.1.12.2
		snmpAgentGroupTable OBJECT-TYPE
			SYNTAX SEQUENCE OF SnmpAgentGroupEntry
			MAX-ACCESS not-accessible
			STATUS current
			DESCRIPTION
				"Description."
			::= { snmpConfigObjects 2 }

		
		-- 1.3.6.1.4.1.34592.1.3.100.1.12.2.1
		snmpAgentGroupEntry OBJECT-TYPE
			SYNTAX SnmpAgentGroupEntry
			MAX-ACCESS not-accessible
			STATUS current
			DESCRIPTION
				"Description."
			INDEX { snmpAgentGroupIndex }
			::= { snmpAgentGroupTable 1 }

		
		SnmpAgentGroupEntry ::=
			SEQUENCE { 
				snmpAgentGroupIndex
					Unsigned32,
				snmpAgentGroupName
					OCTET STRING,
				snmpAgentGroupSecureLevel
					INTEGER,
				snmpAgentGroupReadView
					OCTET STRING,
				snmpAgentGroupWriteView
					OCTET STRING,
				snmpAgentGroupNotifyView
					OCTET STRING,
				snmpAgentGroupRowStatus
					RowStatus
			 }

		-- 1.3.6.1.4.1.34592.1.3.100.1.12.2.1.1
		snmpAgentGroupIndex OBJECT-TYPE
			SYNTAX Unsigned32
			MAX-ACCESS not-accessible
			STATUS current
			DESCRIPTION
				"Description."
			::= { snmpAgentGroupEntry 1 }

		
		-- 1.3.6.1.4.1.34592.1.3.100.1.12.2.1.2
		snmpAgentGroupName OBJECT-TYPE
			SYNTAX OCTET STRING (SIZE (1..32))
			MAX-ACCESS read-create
			STATUS current
			DESCRIPTION
				"Description."
			::= { snmpAgentGroupEntry 2 }

		
		-- 1.3.6.1.4.1.34592.1.3.100.1.12.2.1.3
		snmpAgentGroupSecureLevel OBJECT-TYPE
			SYNTAX INTEGER
				{
				authentication(0),
				noauth(1),
				privacy(2)
				}
			MAX-ACCESS read-create
			STATUS current
			DESCRIPTION
				"Description."
			::= { snmpAgentGroupEntry 3 }

		
		-- 1.3.6.1.4.1.34592.1.3.100.1.12.2.1.4
		snmpAgentGroupReadView OBJECT-TYPE
			SYNTAX OCTET STRING (SIZE (1..32))
			MAX-ACCESS read-create
			STATUS current
			DESCRIPTION
				"Description."
			::= { snmpAgentGroupEntry 4 }

		
		-- 1.3.6.1.4.1.34592.1.3.100.1.12.2.1.5
		snmpAgentGroupWriteView OBJECT-TYPE
			SYNTAX OCTET STRING (SIZE (1..32))
			MAX-ACCESS read-create
			STATUS current
			DESCRIPTION
				"Description."
			::= { snmpAgentGroupEntry 5 }

		
		-- 1.3.6.1.4.1.34592.1.3.100.1.12.2.1.6
		snmpAgentGroupNotifyView OBJECT-TYPE
			SYNTAX OCTET STRING (SIZE (1..32))
			MAX-ACCESS read-create
			STATUS current
			DESCRIPTION
				"Description."
			::= { snmpAgentGroupEntry 6 }

		
		-- 1.3.6.1.4.1.34592.1.3.100.1.12.2.1.7
		snmpAgentGroupRowStatus OBJECT-TYPE
			SYNTAX RowStatus
			MAX-ACCESS read-create
			STATUS current
			DESCRIPTION
				"Description."
			::= { snmpAgentGroupEntry 7 }

		
		-- 1.3.6.1.4.1.34592.1.3.100.1.12.3
		snmpAgentUsmUserTable OBJECT-TYPE
			SYNTAX SEQUENCE OF SnmpAgentUsmUserEntry
			MAX-ACCESS not-accessible
			STATUS current
			DESCRIPTION
				"Description."
			::= { snmpConfigObjects 3 }

		
		-- 1.3.6.1.4.1.34592.1.3.100.1.12.3.1
		snmpAgentUsmUserEntry OBJECT-TYPE
			SYNTAX SnmpAgentUsmUserEntry
			MAX-ACCESS not-accessible
			STATUS current
			DESCRIPTION
				"Description."
			INDEX { snmpAgentUsmUserIndex }
			::= { snmpAgentUsmUserTable 1 }

		
		SnmpAgentUsmUserEntry ::=
			SEQUENCE { 
				snmpAgentUsmUserIndex
					Unsigned32,
				snmpAgentUsmUserName
					OCTET STRING,
				snmpAgentUsmUserGroupName
					OCTET STRING,
				snmpAgentUsmUserAuthMode
					INTEGER,
				snmpAgentUsmUserAuthKey
					OCTET STRING,
				snmpAgentUsmUserPriMode
					INTEGER,
				snmpAgentUsmUserPriKey
					OCTET STRING,
				snmpAgentUsmUserRowStatus
					RowStatus
			 }

		-- 1.3.6.1.4.1.34592.1.3.100.1.12.3.1.1
		snmpAgentUsmUserIndex OBJECT-TYPE
			SYNTAX Unsigned32
			MAX-ACCESS not-accessible
			STATUS current
			DESCRIPTION
				"Description."
			::= { snmpAgentUsmUserEntry 1 }

		
		-- 1.3.6.1.4.1.34592.1.3.100.1.12.3.1.2
		snmpAgentUsmUserName OBJECT-TYPE
			SYNTAX OCTET STRING (SIZE (1..32))
			MAX-ACCESS read-create
			STATUS current
			DESCRIPTION
				"Description."
			::= { snmpAgentUsmUserEntry 2 }

		
		-- 1.3.6.1.4.1.34592.1.3.100.1.12.3.1.3
		snmpAgentUsmUserGroupName OBJECT-TYPE
			SYNTAX OCTET STRING (SIZE (1..32))
			MAX-ACCESS read-create
			STATUS current
			DESCRIPTION
				"Description."
			::= { snmpAgentUsmUserEntry 3 }

		
		-- 1.3.6.1.4.1.34592.1.3.100.1.12.3.1.4
		snmpAgentUsmUserAuthMode OBJECT-TYPE
			SYNTAX INTEGER
				{
				no(0),
				md5(1)
				}
			MAX-ACCESS read-create
			STATUS current
			DESCRIPTION
				"Description."
			::= { snmpAgentUsmUserEntry 4 }

		
		-- 1.3.6.1.4.1.34592.1.3.100.1.12.3.1.5
		snmpAgentUsmUserAuthKey OBJECT-TYPE
			SYNTAX OCTET STRING (SIZE (8..64))
			MAX-ACCESS read-create
			STATUS current
			DESCRIPTION
				"Description."
			::= { snmpAgentUsmUserEntry 5 }

		
		-- 1.3.6.1.4.1.34592.1.3.100.1.12.3.1.6
		snmpAgentUsmUserPriMode OBJECT-TYPE
			SYNTAX INTEGER
				{
				no(0),
				des56(1)
				}
			MAX-ACCESS read-create
			STATUS current
			DESCRIPTION
				"Description."
			::= { snmpAgentUsmUserEntry 6 }

		
		-- 1.3.6.1.4.1.34592.1.3.100.1.12.3.1.7
		snmpAgentUsmUserPriKey OBJECT-TYPE
			SYNTAX OCTET STRING (SIZE (8..64))
			MAX-ACCESS read-create
			STATUS current
			DESCRIPTION
				"Description."
			::= { snmpAgentUsmUserEntry 7 }

		
		-- 1.3.6.1.4.1.34592.1.3.100.1.12.3.1.8
		snmpAgentUsmUserRowStatus OBJECT-TYPE
			SYNTAX RowStatus
			MAX-ACCESS read-create
			STATUS current
			DESCRIPTION
				"Description."
			::= { snmpAgentUsmUserEntry 8 }

		
		-- 1.3.6.1.4.1.34592.1.3.100.1.13
		fanObjects OBJECT IDENTIFIER ::= { systemObjects 13 }

		
		-- 1.3.6.1.4.1.34592.1.3.100.1.13.1
		fanConfigSpeedSupport OBJECT-TYPE
			SYNTAX TruthValue
			MAX-ACCESS read-only
			STATUS current
			DESCRIPTION
				"Description."
			::= { fanObjects 1 }

		
		-- 1.3.6.1.4.1.34592.1.3.100.1.13.2
		fanConfigSpeedMode OBJECT-TYPE
			SYNTAX INTEGER
				{
				auto(1),
				manual(2)
				}
			MAX-ACCESS read-write
			STATUS current
			DESCRIPTION
				"Description."
			::= { fanObjects 2 }

		
		-- 1.3.6.1.4.1.34592.1.3.100.1.13.3
		fanConfigSpeedLevel OBJECT-TYPE
			SYNTAX INTEGER
				{
				level1(1),
				level2(2),
				level3(3),
				level4(4)
				}
			MAX-ACCESS read-write
			STATUS current
			DESCRIPTION
				"Description."
			::= { fanObjects 3 }

		
		-- 1.3.6.1.4.1.34592.1.3.100.1.13.4
		fanSpeedTable OBJECT-TYPE
			SYNTAX SEQUENCE OF FanSpeedEntry
			MAX-ACCESS not-accessible
			STATUS current
			DESCRIPTION
				"Description."
			::= { fanObjects 4 }

		
		-- 1.3.6.1.4.1.34592.1.3.100.1.13.4.1
		fanSpeedEntry OBJECT-TYPE
			SYNTAX FanSpeedEntry
			MAX-ACCESS not-accessible
			STATUS current
			DESCRIPTION
				"Description."
			INDEX { fanIndex }
			::= { fanSpeedTable 1 }

		
		FanSpeedEntry ::=
			SEQUENCE { 
				fanIndex
					INTEGER,
				fanSpeed
					INTEGER
			 }

		-- 1.3.6.1.4.1.34592.1.3.100.1.13.4.1.1
		fanIndex OBJECT-TYPE
			SYNTAX INTEGER
			MAX-ACCESS not-accessible
			STATUS current
			DESCRIPTION
				"Description."
			::= { fanSpeedEntry 1 }

		
		-- 1.3.6.1.4.1.34592.1.3.100.1.13.4.1.2
		fanSpeed OBJECT-TYPE
			SYNTAX INTEGER
			MAX-ACCESS read-only
			STATUS current
			DESCRIPTION
				"Unit:(RPM)"
			::= { fanSpeedEntry 2 }

		
		-- 1.3.6.1.4.1.34592.1.3.100.1.14
		configAutosaveObjects OBJECT IDENTIFIER ::= { systemObjects 14 }

		
		-- 1.3.6.1.4.1.34592.1.3.100.1.14.1
		configAutosaveEnable OBJECT-TYPE
			SYNTAX INTEGER
				{
				disable(0),
				intervalEnable(1),
				timeEnable(2)
				}
			MAX-ACCESS read-write
			STATUS current
			DESCRIPTION
				"Description."
			::= { configAutosaveObjects 1 }

		
		-- 1.3.6.1.4.1.34592.1.3.100.1.14.2
		configAutosaveInterval OBJECT-TYPE
			SYNTAX INTEGER (2..1440)
			MAX-ACCESS read-write
			STATUS current
			DESCRIPTION
				"Interval.(unit:minutes)"
			::= { configAutosaveObjects 2 }

		
		-- 1.3.6.1.4.1.34592.1.3.100.1.14.3
		configAutosaveTime OBJECT-TYPE
			SYNTAX DisplayString (SIZE (5))
			MAX-ACCESS read-write
			STATUS current
			DESCRIPTION
				"Format: HH:MM
				For exmaple: 23:10"
			::= { configAutosaveObjects 3 }

		
		-- 1.3.6.1.4.1.34592.1.3.100.1.15
		batteryBackupUnitObjects OBJECT IDENTIFIER ::= { systemObjects 15 }

		
		-- 1.3.6.1.4.1.34592.1.3.100.1.15.1
		batteryBackupUnitPresenceStatus OBJECT-TYPE
			SYNTAX INTEGER
				{
				absence(0),
				normal(1)
				}
			MAX-ACCESS read-only
			STATUS current
			DESCRIPTION
				"Description."
			::= { batteryBackupUnitObjects 1 }

		
		-- 1.3.6.1.4.1.34592.1.3.100.1.15.2
		batteryBackupUnitWorkStatus OBJECT-TYPE
			SYNTAX INTEGER
				{
				notworking(0),
				working(1)
				}
			MAX-ACCESS read-only
			STATUS current
			DESCRIPTION
				"Description."
			::= { batteryBackupUnitObjects 2 }

		
		-- 1.3.6.1.4.1.34592.1.3.100.1.16
		deviceRateObject OBJECT IDENTIFIER ::= { systemObjects 16 }

		
		-- 1.3.6.1.4.1.34592.1.3.100.1.16.1
		oltPortRateRecordTable OBJECT-TYPE
			SYNTAX SEQUENCE OF OltPortRateRecordEntry
			MAX-ACCESS not-accessible
			STATUS current
			DESCRIPTION
				"Description."
			::= { deviceRateObject 1 }

		
		-- 1.3.6.1.4.1.34592.1.3.100.1.16.1.1
		oltPortRateRecordEntry OBJECT-TYPE
			SYNTAX OltPortRateRecordEntry
			MAX-ACCESS not-accessible
			STATUS current
			DESCRIPTION
				"Description."
			INDEX { ponInfoExtDeviceIndex, ponInfoExtCardIndex, ponInfoExtPortIndex }
			::= { oltPortRateRecordTable 1 }

		
		OltPortRateRecordEntry ::=
			SEQUENCE { 
				oltPortRateRecordUp1
					Counter64,
				oltPortRateRecordUp2
					Counter64,
				oltPortRateRecordUp3
					Counter64,
				oltPortRateRecordUp4
					Counter64,
				oltPortRateRecordUp5
					Counter64,
				oltPortRateRecordUp6
					Counter64,
				oltPortRateRecordUp7
					Counter64,
				oltPortRateRecordUp8
					Counter64,
				oltPortRateRecordUp9
					Counter64,
				oltPortRateRecordUp10
					Counter64,
				oltPortRateRecordUp11
					Counter64,
				oltPortRateRecordUp12
					Counter64,
				oltPortRateRecordUp13
					Counter64,
				oltPortRateRecordUp14
					Counter64,
				oltPortRateRecordUp15
					Counter64,
				oltPortRateRecordUp16
					Counter64,
				oltPortRateRecordUp17
					Counter64,
				oltPortRateRecordUp18
					Counter64,
				oltPortRateRecordUp19
					Counter64,
				oltPortRateRecordUp20
					Counter64,
				oltPortRateRecordUp21
					Counter64,
				oltPortRateRecordUp22
					Counter64,
				oltPortRateRecordUp23
					Counter64,
				oltPortRateRecordUp24
					Counter64,
				oltPortRateRecordUp25
					Counter64,
				oltPortRateRecordUp26
					Counter64,
				oltPortRateRecordUp27
					Counter64,
				oltPortRateRecordUp28
					Counter64,
				oltPortRateRecordUp29
					Counter64,
				oltPortRateRecordUp30
					Counter64,
				oltPortRateRecordDown1
					Counter64,
				oltPortRateRecordDown2
					Counter64,
				oltPortRateRecordDown3
					Counter64,
				oltPortRateRecordDown4
					Counter64,
				oltPortRateRecordDown5
					Counter64,
				oltPortRateRecordDown6
					Counter64,
				oltPortRateRecordDown7
					Counter64,
				oltPortRateRecordDown8
					Counter64,
				oltPortRateRecordDown9
					Counter64,
				oltPortRateRecordDown10
					Counter64,
				oltPortRateRecordDown11
					Counter64,
				oltPortRateRecordDown12
					Counter64,
				oltPortRateRecordDown13
					Counter64,
				oltPortRateRecordDown14
					Counter64,
				oltPortRateRecordDown15
					Counter64,
				oltPortRateRecordDown16
					Counter64,
				oltPortRateRecordDown17
					Counter64,
				oltPortRateRecordDown18
					Counter64,
				oltPortRateRecordDown19
					Counter64,
				oltPortRateRecordDown20
					Counter64,
				oltPortRateRecordDown21
					Counter64,
				oltPortRateRecordDown22
					Counter64,
				oltPortRateRecordDown23
					Counter64,
				oltPortRateRecordDown24
					Counter64,
				oltPortRateRecordDown25
					Counter64,
				oltPortRateRecordDown26
					Counter64,
				oltPortRateRecordDown27
					Counter64,
				oltPortRateRecordDown28
					Counter64,
				oltPortRateRecordDown29
					Counter64,
				oltPortRateRecordDown30
					Counter64
			 }

		-- 1.3.6.1.4.1.34592.1.3.100.1.16.1.1.1
		oltPortRateRecordUp1 OBJECT-TYPE
			SYNTAX Counter64
			MAX-ACCESS read-only
			STATUS current
			DESCRIPTION
				"Description."
			::= { oltPortRateRecordEntry 1 }

		
		-- 1.3.6.1.4.1.34592.1.3.100.1.16.1.1.2
		oltPortRateRecordUp2 OBJECT-TYPE
			SYNTAX Counter64
			MAX-ACCESS read-only
			STATUS current
			DESCRIPTION
				"Description."
			::= { oltPortRateRecordEntry 2 }

		
		-- 1.3.6.1.4.1.34592.1.3.100.1.16.1.1.3
		oltPortRateRecordUp3 OBJECT-TYPE
			SYNTAX Counter64
			MAX-ACCESS read-only
			STATUS current
			DESCRIPTION
				"Description."
			::= { oltPortRateRecordEntry 3 }

		
		-- 1.3.6.1.4.1.34592.1.3.100.1.16.1.1.4
		oltPortRateRecordUp4 OBJECT-TYPE
			SYNTAX Counter64
			MAX-ACCESS read-only
			STATUS current
			DESCRIPTION
				"Description."
			::= { oltPortRateRecordEntry 4 }

		
		-- 1.3.6.1.4.1.34592.1.3.100.1.16.1.1.5
		oltPortRateRecordUp5 OBJECT-TYPE
			SYNTAX Counter64
			MAX-ACCESS read-only
			STATUS current
			DESCRIPTION
				"Description."
			::= { oltPortRateRecordEntry 5 }

		
		-- 1.3.6.1.4.1.34592.1.3.100.1.16.1.1.6
		oltPortRateRecordUp6 OBJECT-TYPE
			SYNTAX Counter64
			MAX-ACCESS read-only
			STATUS current
			DESCRIPTION
				"Description."
			::= { oltPortRateRecordEntry 6 }

		
		-- 1.3.6.1.4.1.34592.1.3.100.1.16.1.1.7
		oltPortRateRecordUp7 OBJECT-TYPE
			SYNTAX Counter64
			MAX-ACCESS read-only
			STATUS current
			DESCRIPTION
				"Description."
			::= { oltPortRateRecordEntry 7 }

		
		-- 1.3.6.1.4.1.34592.1.3.100.1.16.1.1.8
		oltPortRateRecordUp8 OBJECT-TYPE
			SYNTAX Counter64
			MAX-ACCESS read-only
			STATUS current
			DESCRIPTION
				"Description."
			::= { oltPortRateRecordEntry 8 }

		
		-- 1.3.6.1.4.1.34592.1.3.100.1.16.1.1.9
		oltPortRateRecordUp9 OBJECT-TYPE
			SYNTAX Counter64
			MAX-ACCESS read-only
			STATUS current
			DESCRIPTION
				"Description."
			::= { oltPortRateRecordEntry 9 }

		
		-- 1.3.6.1.4.1.34592.1.3.100.1.16.1.1.10
		oltPortRateRecordUp10 OBJECT-TYPE
			SYNTAX Counter64
			MAX-ACCESS read-only
			STATUS current
			DESCRIPTION
				"Description."
			::= { oltPortRateRecordEntry 10 }

		
		-- 1.3.6.1.4.1.34592.1.3.100.1.16.1.1.11
		oltPortRateRecordUp11 OBJECT-TYPE
			SYNTAX Counter64
			MAX-ACCESS read-only
			STATUS current
			DESCRIPTION
				"Description."
			::= { oltPortRateRecordEntry 11 }

		
		-- 1.3.6.1.4.1.34592.1.3.100.1.16.1.1.12
		oltPortRateRecordUp12 OBJECT-TYPE
			SYNTAX Counter64
			MAX-ACCESS read-only
			STATUS current
			DESCRIPTION
				"Description."
			::= { oltPortRateRecordEntry 12 }

		
		-- 1.3.6.1.4.1.34592.1.3.100.1.16.1.1.13
		oltPortRateRecordUp13 OBJECT-TYPE
			SYNTAX Counter64
			MAX-ACCESS read-only
			STATUS current
			DESCRIPTION
				"Description."
			::= { oltPortRateRecordEntry 13 }

		
		-- 1.3.6.1.4.1.34592.1.3.100.1.16.1.1.14
		oltPortRateRecordUp14 OBJECT-TYPE
			SYNTAX Counter64
			MAX-ACCESS read-only
			STATUS current
			DESCRIPTION
				"Description."
			::= { oltPortRateRecordEntry 14 }

		
		-- 1.3.6.1.4.1.34592.1.3.100.1.16.1.1.15
		oltPortRateRecordUp15 OBJECT-TYPE
			SYNTAX Counter64
			MAX-ACCESS read-only
			STATUS current
			DESCRIPTION
				"Description."
			::= { oltPortRateRecordEntry 15 }

		
		-- 1.3.6.1.4.1.34592.1.3.100.1.16.1.1.16
		oltPortRateRecordUp16 OBJECT-TYPE
			SYNTAX Counter64
			MAX-ACCESS read-only
			STATUS current
			DESCRIPTION
				"Description."
			::= { oltPortRateRecordEntry 16 }

		
		-- 1.3.6.1.4.1.34592.1.3.100.1.16.1.1.17
		oltPortRateRecordUp17 OBJECT-TYPE
			SYNTAX Counter64
			MAX-ACCESS read-only
			STATUS current
			DESCRIPTION
				"Description."
			::= { oltPortRateRecordEntry 17 }

		
		-- 1.3.6.1.4.1.34592.1.3.100.1.16.1.1.18
		oltPortRateRecordUp18 OBJECT-TYPE
			SYNTAX Counter64
			MAX-ACCESS read-only
			STATUS current
			DESCRIPTION
				"Description."
			::= { oltPortRateRecordEntry 18 }

		
		-- 1.3.6.1.4.1.34592.1.3.100.1.16.1.1.19
		oltPortRateRecordUp19 OBJECT-TYPE
			SYNTAX Counter64
			MAX-ACCESS read-only
			STATUS current
			DESCRIPTION
				"Description."
			::= { oltPortRateRecordEntry 19 }

		
		-- 1.3.6.1.4.1.34592.1.3.100.1.16.1.1.20
		oltPortRateRecordUp20 OBJECT-TYPE
			SYNTAX Counter64
			MAX-ACCESS read-only
			STATUS current
			DESCRIPTION
				"Description."
			::= { oltPortRateRecordEntry 20 }

		
		-- 1.3.6.1.4.1.34592.1.3.100.1.16.1.1.21
		oltPortRateRecordUp21 OBJECT-TYPE
			SYNTAX Counter64
			MAX-ACCESS read-only
			STATUS current
			DESCRIPTION
				"Description."
			::= { oltPortRateRecordEntry 21 }

		
		-- 1.3.6.1.4.1.34592.1.3.100.1.16.1.1.22
		oltPortRateRecordUp22 OBJECT-TYPE
			SYNTAX Counter64
			MAX-ACCESS read-only
			STATUS current
			DESCRIPTION
				"Description."
			::= { oltPortRateRecordEntry 22 }

		
		-- 1.3.6.1.4.1.34592.1.3.100.1.16.1.1.23
		oltPortRateRecordUp23 OBJECT-TYPE
			SYNTAX Counter64
			MAX-ACCESS read-only
			STATUS current
			DESCRIPTION
				"Description."
			::= { oltPortRateRecordEntry 23 }

		
		-- 1.3.6.1.4.1.34592.1.3.100.1.16.1.1.24
		oltPortRateRecordUp24 OBJECT-TYPE
			SYNTAX Counter64
			MAX-ACCESS read-only
			STATUS current
			DESCRIPTION
				"Description."
			::= { oltPortRateRecordEntry 24 }

		
		-- 1.3.6.1.4.1.34592.1.3.100.1.16.1.1.25
		oltPortRateRecordUp25 OBJECT-TYPE
			SYNTAX Counter64
			MAX-ACCESS read-only
			STATUS current
			DESCRIPTION
				"Description."
			::= { oltPortRateRecordEntry 25 }

		
		-- 1.3.6.1.4.1.34592.1.3.100.1.16.1.1.26
		oltPortRateRecordUp26 OBJECT-TYPE
			SYNTAX Counter64
			MAX-ACCESS read-only
			STATUS current
			DESCRIPTION
				"Description."
			::= { oltPortRateRecordEntry 26 }

		
		-- 1.3.6.1.4.1.34592.1.3.100.1.16.1.1.27
		oltPortRateRecordUp27 OBJECT-TYPE
			SYNTAX Counter64
			MAX-ACCESS read-only
			STATUS current
			DESCRIPTION
				"Description."
			::= { oltPortRateRecordEntry 27 }

		
		-- 1.3.6.1.4.1.34592.1.3.100.1.16.1.1.28
		oltPortRateRecordUp28 OBJECT-TYPE
			SYNTAX Counter64
			MAX-ACCESS read-only
			STATUS current
			DESCRIPTION
				"Description."
			::= { oltPortRateRecordEntry 28 }

		
		-- 1.3.6.1.4.1.34592.1.3.100.1.16.1.1.29
		oltPortRateRecordUp29 OBJECT-TYPE
			SYNTAX Counter64
			MAX-ACCESS read-only
			STATUS current
			DESCRIPTION
				"Description."
			::= { oltPortRateRecordEntry 29 }

		
		-- 1.3.6.1.4.1.34592.1.3.100.1.16.1.1.30
		oltPortRateRecordUp30 OBJECT-TYPE
			SYNTAX Counter64
			MAX-ACCESS read-only
			STATUS current
			DESCRIPTION
				"Description."
			::= { oltPortRateRecordEntry 30 }

		
		-- 1.3.6.1.4.1.34592.1.3.100.1.16.1.1.31
		oltPortRateRecordDown1 OBJECT-TYPE
			SYNTAX Counter64
			MAX-ACCESS read-only
			STATUS current
			DESCRIPTION
				"Description."
			::= { oltPortRateRecordEntry 31 }

		
		-- 1.3.6.1.4.1.34592.1.3.100.1.16.1.1.32
		oltPortRateRecordDown2 OBJECT-TYPE
			SYNTAX Counter64
			MAX-ACCESS read-only
			STATUS current
			DESCRIPTION
				"Description."
			::= { oltPortRateRecordEntry 32 }

		
		-- 1.3.6.1.4.1.34592.1.3.100.1.16.1.1.33
		oltPortRateRecordDown3 OBJECT-TYPE
			SYNTAX Counter64
			MAX-ACCESS read-only
			STATUS current
			DESCRIPTION
				"Description."
			::= { oltPortRateRecordEntry 33 }

		
		-- 1.3.6.1.4.1.34592.1.3.100.1.16.1.1.34
		oltPortRateRecordDown4 OBJECT-TYPE
			SYNTAX Counter64
			MAX-ACCESS read-only
			STATUS current
			DESCRIPTION
				"Description."
			::= { oltPortRateRecordEntry 34 }

		
		-- 1.3.6.1.4.1.34592.1.3.100.1.16.1.1.35
		oltPortRateRecordDown5 OBJECT-TYPE
			SYNTAX Counter64
			MAX-ACCESS read-only
			STATUS current
			DESCRIPTION
				"Description."
			::= { oltPortRateRecordEntry 35 }

		
		-- 1.3.6.1.4.1.34592.1.3.100.1.16.1.1.36
		oltPortRateRecordDown6 OBJECT-TYPE
			SYNTAX Counter64
			MAX-ACCESS read-only
			STATUS current
			DESCRIPTION
				"Description."
			::= { oltPortRateRecordEntry 36 }

		
		-- 1.3.6.1.4.1.34592.1.3.100.1.16.1.1.37
		oltPortRateRecordDown7 OBJECT-TYPE
			SYNTAX Counter64
			MAX-ACCESS read-only
			STATUS current
			DESCRIPTION
				"Description."
			::= { oltPortRateRecordEntry 37 }

		
		-- 1.3.6.1.4.1.34592.1.3.100.1.16.1.1.38
		oltPortRateRecordDown8 OBJECT-TYPE
			SYNTAX Counter64
			MAX-ACCESS read-only
			STATUS current
			DESCRIPTION
				"Description."
			::= { oltPortRateRecordEntry 38 }

		
		-- 1.3.6.1.4.1.34592.1.3.100.1.16.1.1.39
		oltPortRateRecordDown9 OBJECT-TYPE
			SYNTAX Counter64
			MAX-ACCESS read-only
			STATUS current
			DESCRIPTION
				"Description."
			::= { oltPortRateRecordEntry 39 }

		
		-- 1.3.6.1.4.1.34592.1.3.100.1.16.1.1.40
		oltPortRateRecordDown10 OBJECT-TYPE
			SYNTAX Counter64
			MAX-ACCESS read-only
			STATUS current
			DESCRIPTION
				"Description."
			::= { oltPortRateRecordEntry 40 }

		
		-- 1.3.6.1.4.1.34592.1.3.100.1.16.1.1.41
		oltPortRateRecordDown11 OBJECT-TYPE
			SYNTAX Counter64
			MAX-ACCESS read-only
			STATUS current
			DESCRIPTION
				"Description."
			::= { oltPortRateRecordEntry 41 }

		
		-- 1.3.6.1.4.1.34592.1.3.100.1.16.1.1.42
		oltPortRateRecordDown12 OBJECT-TYPE
			SYNTAX Counter64
			MAX-ACCESS read-only
			STATUS current
			DESCRIPTION
				"Description."
			::= { oltPortRateRecordEntry 42 }

		
		-- 1.3.6.1.4.1.34592.1.3.100.1.16.1.1.43
		oltPortRateRecordDown13 OBJECT-TYPE
			SYNTAX Counter64
			MAX-ACCESS read-only
			STATUS current
			DESCRIPTION
				"Description."
			::= { oltPortRateRecordEntry 43 }

		
		-- 1.3.6.1.4.1.34592.1.3.100.1.16.1.1.44
		oltPortRateRecordDown14 OBJECT-TYPE
			SYNTAX Counter64
			MAX-ACCESS read-only
			STATUS current
			DESCRIPTION
				"Description."
			::= { oltPortRateRecordEntry 44 }

		
		-- 1.3.6.1.4.1.34592.1.3.100.1.16.1.1.45
		oltPortRateRecordDown15 OBJECT-TYPE
			SYNTAX Counter64
			MAX-ACCESS read-only
			STATUS current
			DESCRIPTION
				"Description."
			::= { oltPortRateRecordEntry 45 }

		
		-- 1.3.6.1.4.1.34592.1.3.100.1.16.1.1.46
		oltPortRateRecordDown16 OBJECT-TYPE
			SYNTAX Counter64
			MAX-ACCESS read-only
			STATUS current
			DESCRIPTION
				"Description."
			::= { oltPortRateRecordEntry 46 }

		
		-- 1.3.6.1.4.1.34592.1.3.100.1.16.1.1.47
		oltPortRateRecordDown17 OBJECT-TYPE
			SYNTAX Counter64
			MAX-ACCESS read-only
			STATUS current
			DESCRIPTION
				"Description."
			::= { oltPortRateRecordEntry 47 }

		
		-- 1.3.6.1.4.1.34592.1.3.100.1.16.1.1.48
		oltPortRateRecordDown18 OBJECT-TYPE
			SYNTAX Counter64
			MAX-ACCESS read-only
			STATUS current
			DESCRIPTION
				"Description."
			::= { oltPortRateRecordEntry 48 }

		
		-- 1.3.6.1.4.1.34592.1.3.100.1.16.1.1.49
		oltPortRateRecordDown19 OBJECT-TYPE
			SYNTAX Counter64
			MAX-ACCESS read-only
			STATUS current
			DESCRIPTION
				"Description."
			::= { oltPortRateRecordEntry 49 }

		
		-- 1.3.6.1.4.1.34592.1.3.100.1.16.1.1.50
		oltPortRateRecordDown20 OBJECT-TYPE
			SYNTAX Counter64
			MAX-ACCESS read-only
			STATUS current
			DESCRIPTION
				"Description."
			::= { oltPortRateRecordEntry 50 }

		
		-- 1.3.6.1.4.1.34592.1.3.100.1.16.1.1.51
		oltPortRateRecordDown21 OBJECT-TYPE
			SYNTAX Counter64
			MAX-ACCESS read-only
			STATUS current
			DESCRIPTION
				"Description."
			::= { oltPortRateRecordEntry 51 }

		
		-- 1.3.6.1.4.1.34592.1.3.100.1.16.1.1.52
		oltPortRateRecordDown22 OBJECT-TYPE
			SYNTAX Counter64
			MAX-ACCESS read-only
			STATUS current
			DESCRIPTION
				"Description."
			::= { oltPortRateRecordEntry 52 }

		
		-- 1.3.6.1.4.1.34592.1.3.100.1.16.1.1.53
		oltPortRateRecordDown23 OBJECT-TYPE
			SYNTAX Counter64
			MAX-ACCESS read-only
			STATUS current
			DESCRIPTION
				"Description."
			::= { oltPortRateRecordEntry 53 }

		
		-- 1.3.6.1.4.1.34592.1.3.100.1.16.1.1.54
		oltPortRateRecordDown24 OBJECT-TYPE
			SYNTAX Counter64
			MAX-ACCESS read-only
			STATUS current
			DESCRIPTION
				"Description."
			::= { oltPortRateRecordEntry 54 }

		
		-- 1.3.6.1.4.1.34592.1.3.100.1.16.1.1.55
		oltPortRateRecordDown25 OBJECT-TYPE
			SYNTAX Counter64
			MAX-ACCESS read-only
			STATUS current
			DESCRIPTION
				"Description."
			::= { oltPortRateRecordEntry 55 }

		
		-- 1.3.6.1.4.1.34592.1.3.100.1.16.1.1.56
		oltPortRateRecordDown26 OBJECT-TYPE
			SYNTAX Counter64
			MAX-ACCESS read-only
			STATUS current
			DESCRIPTION
				"Description."
			::= { oltPortRateRecordEntry 56 }

		
		-- 1.3.6.1.4.1.34592.1.3.100.1.16.1.1.57
		oltPortRateRecordDown27 OBJECT-TYPE
			SYNTAX Counter64
			MAX-ACCESS read-only
			STATUS current
			DESCRIPTION
				"Description."
			::= { oltPortRateRecordEntry 57 }

		
		-- 1.3.6.1.4.1.34592.1.3.100.1.16.1.1.58
		oltPortRateRecordDown28 OBJECT-TYPE
			SYNTAX Counter64
			MAX-ACCESS read-only
			STATUS current
			DESCRIPTION
				"Description."
			::= { oltPortRateRecordEntry 58 }

		
		-- 1.3.6.1.4.1.34592.1.3.100.1.16.1.1.59
		oltPortRateRecordDown29 OBJECT-TYPE
			SYNTAX Counter64
			MAX-ACCESS read-only
			STATUS current
			DESCRIPTION
				"Description."
			::= { oltPortRateRecordEntry 59 }

		
		-- 1.3.6.1.4.1.34592.1.3.100.1.16.1.1.60
		oltPortRateRecordDown30 OBJECT-TYPE
			SYNTAX Counter64
			MAX-ACCESS read-only
			STATUS current
			DESCRIPTION
				"Description."
			::= { oltPortRateRecordEntry 60 }

		
		-- 1.3.6.1.4.1.34592.1.3.100.1.17
		systemUpgradeObjects OBJECT IDENTIFIER ::= { systemObjects 17 }

		
		-- 1.3.6.1.4.1.34592.1.3.100.1.17.1
		systemUpgradeStatus OBJECT-TYPE
			SYNTAX INTEGER
				{
				idle(0),
				inProgress(1),
				success(2),
				fail(3),
				partial(4)
				}
			MAX-ACCESS read-only
			STATUS current
			DESCRIPTION
				"Description."
			::= { systemUpgradeObjects 1 }

		
		-- 1.3.6.1.4.1.34592.1.3.100.1.17.2
		systemUpgradeProgress OBJECT-TYPE
			SYNTAX Integer32
			MAX-ACCESS read-only
			STATUS current
			DESCRIPTION
				"Description."
			::= { systemUpgradeObjects 2 }

		
		-- 1.3.6.1.4.1.34592.1.3.100.1.18
		dstTable OBJECT-TYPE
			SYNTAX SEQUENCE OF DstEntry
			MAX-ACCESS not-accessible
			STATUS current
			DESCRIPTION
				"Description."
			::= { systemObjects 18 }

		
		-- 1.3.6.1.4.1.34592.1.3.100.1.18.1
		dstEntry OBJECT-TYPE
			SYNTAX DstEntry
			MAX-ACCESS not-accessible
			STATUS current
			DESCRIPTION
				"Description."
			INDEX { ponInfoExtDeviceIndex }
			::= { dstTable 1 }

		
		DstEntry ::=
			SEQUENCE { 
				dstStartMonth
					Integer32,
				dstStartWeek
					INTEGER,
				dstStartDay
					INTEGER,
				dstStartTime
					OCTET STRING,
				dstEndStartMonth
					Integer32,
				dstEndStartWeek
					INTEGER,
				dstEndDay
					INTEGER,
				dstEndStartTime
					OCTET STRING,
				dstTimeAdjust
					OCTET STRING,
				dstClear
					Integer32
			 }

		-- 1.3.6.1.4.1.34592.1.3.100.1.18.1.1
		dstStartMonth OBJECT-TYPE
			SYNTAX Integer32 (1..12)
			MAX-ACCESS read-write
			STATUS current
			DESCRIPTION
				"Description."
			::= { dstEntry 1 }

		
		-- 1.3.6.1.4.1.34592.1.3.100.1.18.1.2
		dstStartWeek OBJECT-TYPE
			SYNTAX INTEGER
				{
				First(1),
				Second(2),
				Third(3),
				Fourth(4),
				Last(5)
				}
			MAX-ACCESS read-write
			STATUS current
			DESCRIPTION
				"Description."
			::= { dstEntry 2 }

		
		-- 1.3.6.1.4.1.34592.1.3.100.1.18.1.3
		dstStartDay OBJECT-TYPE
			SYNTAX INTEGER
				{
				Sunday(0),
				Monday(1),
				Tuesday(2),
				Wednesday(3),
				Thursday(4),
				Friday(5),
				Saturday(6)
				}
			MAX-ACCESS read-write
			STATUS current
			DESCRIPTION
				"Description."
			::= { dstEntry 3 }

		
		-- 1.3.6.1.4.1.34592.1.3.100.1.18.1.4
		dstStartTime OBJECT-TYPE
			SYNTAX OCTET STRING
			MAX-ACCESS read-write
			STATUS current
			DESCRIPTION
				"Description."
			::= { dstEntry 4 }

		
		-- 1.3.6.1.4.1.34592.1.3.100.1.18.1.5
		dstEndStartMonth OBJECT-TYPE
			SYNTAX Integer32 (1..12)
			MAX-ACCESS read-write
			STATUS current
			DESCRIPTION
				"Description."
			::= { dstEntry 5 }

		
		-- 1.3.6.1.4.1.34592.1.3.100.1.18.1.6
		dstEndStartWeek OBJECT-TYPE
			SYNTAX INTEGER
				{
				First(1),
				Second(2),
				Third(3),
				Fourth(4),
				Last(5)
				}
			MAX-ACCESS read-write
			STATUS current
			DESCRIPTION
				"Description."
			::= { dstEntry 6 }

		
		-- 1.3.6.1.4.1.34592.1.3.100.1.18.1.7
		dstEndDay OBJECT-TYPE
			SYNTAX INTEGER
				{
				Sunday(0),
				Monday(1),
				Tuesday(2),
				Wednesday(3),
				Thursday(4),
				Friday(5),
				Saturday(6)
				}
			MAX-ACCESS read-write
			STATUS current
			DESCRIPTION
				"Description."
			::= { dstEntry 7 }

		
		-- 1.3.6.1.4.1.34592.1.3.100.1.18.1.8
		dstEndStartTime OBJECT-TYPE
			SYNTAX OCTET STRING
			MAX-ACCESS read-write
			STATUS current
			DESCRIPTION
				"Description."
			::= { dstEntry 8 }

		
		-- 1.3.6.1.4.1.34592.1.3.100.1.18.1.9
		dstTimeAdjust OBJECT-TYPE
			SYNTAX OCTET STRING
			MAX-ACCESS read-write
			STATUS current
			DESCRIPTION
				"Description."
			::= { dstEntry 9 }

		
		-- 1.3.6.1.4.1.34592.1.3.100.1.18.1.10
		dstClear OBJECT-TYPE
			SYNTAX Integer32
			MAX-ACCESS read-write
			STATUS current
			DESCRIPTION
				"Description."
			::= { dstEntry 10 }

		
		-- 1.3.6.1.4.1.34592.1.3.100.1.19
		aaaManagementObjects OBJECT IDENTIFIER ::= { systemObjects 19 }

		
		-- 1.3.6.1.4.1.34592.1.3.100.1.19.1
		aaaProtocol OBJECT-TYPE
			SYNTAX INTEGER
				{
				radius(1),
				tacacs(2),
				unknown(3)
				}
			MAX-ACCESS read-write
			STATUS current
			DESCRIPTION
				"Description."
			::= { aaaManagementObjects 1 }

		
		-- 1.3.6.1.4.1.34592.1.3.100.1.19.2
		radiusServerIp OBJECT-TYPE
			SYNTAX IpAddress
			MAX-ACCESS read-write
			STATUS current
			DESCRIPTION
				"Description."
			::= { aaaManagementObjects 2 }

		
		-- 1.3.6.1.4.1.34592.1.3.100.1.19.3
		radiusServerShareKey OBJECT-TYPE
			SYNTAX OCTET STRING
			MAX-ACCESS read-write
			STATUS current
			DESCRIPTION
				"Description."
			::= { aaaManagementObjects 3 }

		
		-- 1.3.6.1.4.1.34592.1.3.100.1.19.4
		tacacsServerIp OBJECT-TYPE
			SYNTAX IpAddress
			MAX-ACCESS read-write
			STATUS current
			DESCRIPTION
				"Description."
			::= { aaaManagementObjects 4 }

		
		-- 1.3.6.1.4.1.34592.1.3.100.1.19.5
		tacacsServerShareKey OBJECT-TYPE
			SYNTAX OCTET STRING
			MAX-ACCESS read-write
			STATUS current
			DESCRIPTION
				"Description."
			::= { aaaManagementObjects 5 }

		
		-- 1.3.6.1.4.1.34592.1.3.100.1.19.6
		aaaDomainTable OBJECT-TYPE
			SYNTAX SEQUENCE OF AaaDomainEntry
			MAX-ACCESS not-accessible
			STATUS current
			DESCRIPTION
				"Description."
			::= { aaaManagementObjects 6 }

		
		-- 1.3.6.1.4.1.34592.1.3.100.1.19.6.1
		aaaDomainEntry OBJECT-TYPE
			SYNTAX AaaDomainEntry
			MAX-ACCESS not-accessible
			STATUS current
			DESCRIPTION
				"Description."
			INDEX { aaaDomainIndex, aaaDomainDeviceIndex }
			::= { aaaDomainTable 1 }

		
		AaaDomainEntry ::=
			SEQUENCE { 
				aaaDomainDeviceIndex
					Integer32,
				aaaDomainIndex
					Integer32,
				aaaDomainName
					DisplayString,
				aaaDomainProtocol
					INTEGER,
				aaaDomainAuthenticationMode
					INTEGER,
				aaaDomainAuthtype
					INTEGER,
				aaaDomainRadiusAccountingServiceId
					DisplayString,
				aaaDomainRadiusAuthenticationServiceId
					DisplayString,
				aaaDomainTacacsAccountingServiceId
					DisplayString,
				aaaDomainTacacsAuthenticationServiceId
					DisplayString,
				aaaDomainTacacsAuthorizeServiceId
					DisplayString,
				aaaDomainRowStatus
					RowStatus
			 }

		-- 1.3.6.1.4.1.34592.1.3.100.1.19.6.1.1
		aaaDomainDeviceIndex OBJECT-TYPE
			SYNTAX Integer32
			MAX-ACCESS not-accessible
			STATUS current
			DESCRIPTION
				"Description."
			::= { aaaDomainEntry 1 }

		
		-- 1.3.6.1.4.1.34592.1.3.100.1.19.6.1.2
		aaaDomainIndex OBJECT-TYPE
			SYNTAX Integer32
			MAX-ACCESS not-accessible
			STATUS current
			DESCRIPTION
				"Description."
			::= { aaaDomainEntry 2 }

		
		-- 1.3.6.1.4.1.34592.1.3.100.1.19.6.1.3
		aaaDomainName OBJECT-TYPE
			SYNTAX DisplayString
			MAX-ACCESS read-create
			STATUS current
			DESCRIPTION
				"Description."
			::= { aaaDomainEntry 3 }

		
		-- 1.3.6.1.4.1.34592.1.3.100.1.19.6.1.4
		aaaDomainProtocol OBJECT-TYPE
			SYNTAX INTEGER
				{
				radius(1),
				tacacs+(2)
				}
			MAX-ACCESS read-write
			STATUS current
			DESCRIPTION
				"Description."
			::= { aaaDomainEntry 4 }

		
		-- 1.3.6.1.4.1.34592.1.3.100.1.19.6.1.5
		aaaDomainAuthenticationMode OBJECT-TYPE
			SYNTAX INTEGER
				{
				Independent(1),
				Primary-Backup(2),
				Multi-Account(3)
				}
			MAX-ACCESS read-write
			STATUS current
			DESCRIPTION
				"Description."
			::= { aaaDomainEntry 5 }

		
		-- 1.3.6.1.4.1.34592.1.3.100.1.19.6.1.6
		aaaDomainAuthtype OBJECT-TYPE
			SYNTAX INTEGER
				{
				acsii(1),
				chap(2),
				pap(3)
				}
			MAX-ACCESS read-write
			STATUS current
			DESCRIPTION
				"Description."
			::= { aaaDomainEntry 6 }

		
		-- 1.3.6.1.4.1.34592.1.3.100.1.19.6.1.7
		aaaDomainRadiusAccountingServiceId OBJECT-TYPE
			SYNTAX DisplayString
			MAX-ACCESS read-write
			STATUS current
			DESCRIPTION
				"Description."
			::= { aaaDomainEntry 7 }

		
		-- 1.3.6.1.4.1.34592.1.3.100.1.19.6.1.8
		aaaDomainRadiusAuthenticationServiceId OBJECT-TYPE
			SYNTAX DisplayString
			MAX-ACCESS read-write
			STATUS current
			DESCRIPTION
				"Description."
			::= { aaaDomainEntry 8 }

		
		-- 1.3.6.1.4.1.34592.1.3.100.1.19.6.1.9
		aaaDomainTacacsAccountingServiceId OBJECT-TYPE
			SYNTAX DisplayString
			MAX-ACCESS read-write
			STATUS current
			DESCRIPTION
				"Description."
			::= { aaaDomainEntry 9 }

		
		-- 1.3.6.1.4.1.34592.1.3.100.1.19.6.1.10
		aaaDomainTacacsAuthenticationServiceId OBJECT-TYPE
			SYNTAX DisplayString
			MAX-ACCESS read-write
			STATUS current
			DESCRIPTION
				"Description."
			::= { aaaDomainEntry 10 }

		
		-- 1.3.6.1.4.1.34592.1.3.100.1.19.6.1.11
		aaaDomainTacacsAuthorizeServiceId OBJECT-TYPE
			SYNTAX DisplayString
			MAX-ACCESS read-write
			STATUS current
			DESCRIPTION
				"Description."
			::= { aaaDomainEntry 11 }

		
		-- 1.3.6.1.4.1.34592.1.3.100.1.19.6.1.12
		aaaDomainRowStatus OBJECT-TYPE
			SYNTAX RowStatus
				{
				active(1),
				notInService(2),
				notReady(3),
				createAndGo(4),
				createAndWait(5),
				destroy(6)
				}
			MAX-ACCESS read-create
			STATUS current
			DESCRIPTION
				"Description."
			::= { aaaDomainEntry 12 }

		
		-- 1.3.6.1.4.1.34592.1.3.100.1.19.7
		radiusAccountingTable OBJECT-TYPE
			SYNTAX SEQUENCE OF RadiusAccountingEntry
			MAX-ACCESS not-accessible
			STATUS current
			DESCRIPTION
				"Description."
			::= { aaaManagementObjects 7 }

		
		-- 1.3.6.1.4.1.34592.1.3.100.1.19.7.1
		radiusAccountingEntry OBJECT-TYPE
			SYNTAX RadiusAccountingEntry
			MAX-ACCESS not-accessible
			STATUS current
			DESCRIPTION
				"Description."
			INDEX { radiusAccountingIndex }
			::= { radiusAccountingTable 1 }

		
		RadiusAccountingEntry ::=
			SEQUENCE { 
				radiusAccountingIndex
					Integer32,
				radiusAccountingIp
					IpAddress,
				radiusAccountingShareKey
					DisplayString,
				radiusAccountingPort
					Integer32,
				radiusAccountingTimeout
					Integer32,
				radiusAccountingRetransmit
					Integer32,
				radiusAccountingRowStatus
					RowStatus
			 }

		-- 1.3.6.1.4.1.34592.1.3.100.1.19.7.1.1
		radiusAccountingIndex OBJECT-TYPE
			SYNTAX Integer32
			MAX-ACCESS not-accessible
			STATUS current
			DESCRIPTION
				"Description."
			::= { radiusAccountingEntry 1 }

		
		-- 1.3.6.1.4.1.34592.1.3.100.1.19.7.1.2
		radiusAccountingIp OBJECT-TYPE
			SYNTAX IpAddress
			MAX-ACCESS read-write
			STATUS current
			DESCRIPTION
				"Description."
			::= { radiusAccountingEntry 2 }

		
		-- 1.3.6.1.4.1.34592.1.3.100.1.19.7.1.3
		radiusAccountingShareKey OBJECT-TYPE
			SYNTAX DisplayString
			MAX-ACCESS read-write
			STATUS current
			DESCRIPTION
				"Description."
			::= { radiusAccountingEntry 3 }

		
		-- 1.3.6.1.4.1.34592.1.3.100.1.19.7.1.4
		radiusAccountingPort OBJECT-TYPE
			SYNTAX Integer32
			MAX-ACCESS read-write
			STATUS current
			DESCRIPTION
				"Description."
			::= { radiusAccountingEntry 4 }

		
		-- 1.3.6.1.4.1.34592.1.3.100.1.19.7.1.5
		radiusAccountingTimeout OBJECT-TYPE
			SYNTAX Integer32
			MAX-ACCESS read-only
			STATUS current
			DESCRIPTION
				"Description."
			::= { radiusAccountingEntry 5 }

		
		-- 1.3.6.1.4.1.34592.1.3.100.1.19.7.1.6
		radiusAccountingRetransmit OBJECT-TYPE
			SYNTAX Integer32
			MAX-ACCESS read-only
			STATUS current
			DESCRIPTION
				"Description."
			::= { radiusAccountingEntry 6 }

		
		-- 1.3.6.1.4.1.34592.1.3.100.1.19.7.1.7
		radiusAccountingRowStatus OBJECT-TYPE
			SYNTAX RowStatus
				{
				active(1),
				notInService(2),
				notReady(3),
				createAndGo(4),
				createAndWait(5),
				destroy(6)
				}
			MAX-ACCESS read-create
			STATUS current
			DESCRIPTION
				"Description."
			::= { radiusAccountingEntry 7 }

		
		-- 1.3.6.1.4.1.34592.1.3.100.1.19.8
		radiusAuthenticationTable OBJECT-TYPE
			SYNTAX SEQUENCE OF RadiusAuthenticationEntry
			MAX-ACCESS not-accessible
			STATUS current
			DESCRIPTION
				"Description."
			::= { aaaManagementObjects 8 }

		
		-- 1.3.6.1.4.1.34592.1.3.100.1.19.8.1
		radiusAuthenticationEntry OBJECT-TYPE
			SYNTAX RadiusAuthenticationEntry
			MAX-ACCESS not-accessible
			STATUS current
			DESCRIPTION
				"Description."
			INDEX { radiusAuthenticationIndex }
			::= { radiusAuthenticationTable 1 }

		
		RadiusAuthenticationEntry ::=
			SEQUENCE { 
				radiusAuthenticationIndex
					Integer32,
				radiusAuthenticationIp
					IpAddress,
				radiusAuthenticationShareKey
					DisplayString,
				radiusAuthenticationPort
					Integer32,
				radiusAuthenticationTimeout
					Integer32,
				radiusAuthenticationRetransmit
					Integer32,
				radiusAuthenticationRowStatus
					RowStatus
			 }

		-- 1.3.6.1.4.1.34592.1.3.100.1.19.8.1.1
		radiusAuthenticationIndex OBJECT-TYPE
			SYNTAX Integer32
			MAX-ACCESS not-accessible
			STATUS current
			DESCRIPTION
				"Description."
			::= { radiusAuthenticationEntry 1 }

		
		-- 1.3.6.1.4.1.34592.1.3.100.1.19.8.1.2
		radiusAuthenticationIp OBJECT-TYPE
			SYNTAX IpAddress
			MAX-ACCESS read-write
			STATUS current
			DESCRIPTION
				"Description."
			::= { radiusAuthenticationEntry 2 }

		
		-- 1.3.6.1.4.1.34592.1.3.100.1.19.8.1.3
		radiusAuthenticationShareKey OBJECT-TYPE
			SYNTAX DisplayString
			MAX-ACCESS read-write
			STATUS current
			DESCRIPTION
				"Description."
			::= { radiusAuthenticationEntry 3 }

		
		-- 1.3.6.1.4.1.34592.1.3.100.1.19.8.1.4
		radiusAuthenticationPort OBJECT-TYPE
			SYNTAX Integer32
			MAX-ACCESS read-write
			STATUS current
			DESCRIPTION
				"Description."
			::= { radiusAuthenticationEntry 4 }

		
		-- 1.3.6.1.4.1.34592.1.3.100.1.19.8.1.5
		radiusAuthenticationTimeout OBJECT-TYPE
			SYNTAX Integer32
			MAX-ACCESS read-only
			STATUS current
			DESCRIPTION
				"Description."
			::= { radiusAuthenticationEntry 5 }

		
		-- 1.3.6.1.4.1.34592.1.3.100.1.19.8.1.6
		radiusAuthenticationRetransmit OBJECT-TYPE
			SYNTAX Integer32
			MAX-ACCESS read-only
			STATUS current
			DESCRIPTION
				"Description."
			::= { radiusAuthenticationEntry 6 }

		
		-- 1.3.6.1.4.1.34592.1.3.100.1.19.8.1.7
		radiusAuthenticationRowStatus OBJECT-TYPE
			SYNTAX RowStatus
				{
				active(1),
				notInService(2),
				notReady(3),
				createAndGo(4),
				createAndWait(5),
				destroy(6)
				}
			MAX-ACCESS read-create
			STATUS current
			DESCRIPTION
				"Description."
			::= { radiusAuthenticationEntry 7 }

		
		-- 1.3.6.1.4.1.34592.1.3.100.1.19.9
		tacacsAuthenticationTable OBJECT-TYPE
			SYNTAX SEQUENCE OF TacacsAuthenticationEntry
			MAX-ACCESS not-accessible
			STATUS current
			DESCRIPTION
				"Description."
			::= { aaaManagementObjects 9 }

		
		-- 1.3.6.1.4.1.34592.1.3.100.1.19.9.1
		tacacsAuthenticationEntry OBJECT-TYPE
			SYNTAX TacacsAuthenticationEntry
			MAX-ACCESS not-accessible
			STATUS current
			DESCRIPTION
				"Description."
			INDEX { tacacsAuthenticationIndex }
			::= { tacacsAuthenticationTable 1 }

		
		TacacsAuthenticationEntry ::=
			SEQUENCE { 
				tacacsAuthenticationIndex
					Integer32,
				tacacsAuthenticationIp
					IpAddress,
				tacacsAuthenticationShareKey
					DisplayString,
				tacacsAuthenticationPort
					Integer32,
				tacacsAuthenticationRowStatus
					RowStatus
			 }

		-- 1.3.6.1.4.1.34592.1.3.100.1.19.9.1.1
		tacacsAuthenticationIndex OBJECT-TYPE
			SYNTAX Integer32
			MAX-ACCESS not-accessible
			STATUS current
			DESCRIPTION
				"Description."
			::= { tacacsAuthenticationEntry 1 }

		
		-- 1.3.6.1.4.1.34592.1.3.100.1.19.9.1.2
		tacacsAuthenticationIp OBJECT-TYPE
			SYNTAX IpAddress
			MAX-ACCESS read-write
			STATUS current
			DESCRIPTION
				"Description."
			::= { tacacsAuthenticationEntry 2 }

		
		-- 1.3.6.1.4.1.34592.1.3.100.1.19.9.1.3
		tacacsAuthenticationShareKey OBJECT-TYPE
			SYNTAX DisplayString
			MAX-ACCESS read-write
			STATUS current
			DESCRIPTION
				"Description."
			::= { tacacsAuthenticationEntry 3 }

		
		-- 1.3.6.1.4.1.34592.1.3.100.1.19.9.1.4
		tacacsAuthenticationPort OBJECT-TYPE
			SYNTAX Integer32
			MAX-ACCESS read-write
			STATUS current
			DESCRIPTION
				"Description."
			::= { tacacsAuthenticationEntry 4 }

		
		-- 1.3.6.1.4.1.34592.1.3.100.1.19.9.1.5
		tacacsAuthenticationRowStatus OBJECT-TYPE
			SYNTAX RowStatus
				{
				active(1),
				notInService(2),
				notReady(3),
				createAndGo(4),
				createAndWait(5),
				destroy(6)
				}
			MAX-ACCESS read-create
			STATUS current
			DESCRIPTION
				"Description."
			::= { tacacsAuthenticationEntry 5 }

		
		-- 1.3.6.1.4.1.34592.1.3.100.1.19.10
		tacacsAuthorizationTable OBJECT-TYPE
			SYNTAX SEQUENCE OF TacacsAuthorizationEntry
			MAX-ACCESS not-accessible
			STATUS current
			DESCRIPTION
				"Description."
			::= { aaaManagementObjects 10 }

		
		-- 1.3.6.1.4.1.34592.1.3.100.1.19.10.1
		tacacsAuthorizationEntry OBJECT-TYPE
			SYNTAX TacacsAuthorizationEntry
			MAX-ACCESS not-accessible
			STATUS current
			DESCRIPTION
				"Description."
			INDEX { tacacsAuthorizationIndex }
			::= { tacacsAuthorizationTable 1 }

		
		TacacsAuthorizationEntry ::=
			SEQUENCE { 
				tacacsAuthorizationIndex
					Integer32,
				tacacsAuthorizationIp
					IpAddress,
				tacacsAuthorizationShareKey
					DisplayString,
				tacacsAuthorizationPort
					Integer32,
				tacacsAuthorizationRowStatus
					RowStatus
			 }

		-- 1.3.6.1.4.1.34592.1.3.100.1.19.10.1.1
		tacacsAuthorizationIndex OBJECT-TYPE
			SYNTAX Integer32
			MAX-ACCESS not-accessible
			STATUS current
			DESCRIPTION
				"Description."
			::= { tacacsAuthorizationEntry 1 }

		
		-- 1.3.6.1.4.1.34592.1.3.100.1.19.10.1.2
		tacacsAuthorizationIp OBJECT-TYPE
			SYNTAX IpAddress
			MAX-ACCESS read-write
			STATUS current
			DESCRIPTION
				"Description."
			::= { tacacsAuthorizationEntry 2 }

		
		-- 1.3.6.1.4.1.34592.1.3.100.1.19.10.1.3
		tacacsAuthorizationShareKey OBJECT-TYPE
			SYNTAX DisplayString
			MAX-ACCESS read-write
			STATUS current
			DESCRIPTION
				"Description."
			::= { tacacsAuthorizationEntry 3 }

		
		-- 1.3.6.1.4.1.34592.1.3.100.1.19.10.1.4
		tacacsAuthorizationPort OBJECT-TYPE
			SYNTAX Integer32
			MAX-ACCESS read-write
			STATUS current
			DESCRIPTION
				"Description."
			::= { tacacsAuthorizationEntry 4 }

		
		-- 1.3.6.1.4.1.34592.1.3.100.1.19.10.1.5
		tacacsAuthorizationRowStatus OBJECT-TYPE
			SYNTAX RowStatus
				{
				active(1),
				notInService(2),
				notReady(3),
				createAndGo(4),
				createAndWait(5),
				destroy(6)
				}
			MAX-ACCESS read-create
			STATUS current
			DESCRIPTION
				"Description."
			::= { tacacsAuthorizationEntry 5 }

		
		-- 1.3.6.1.4.1.34592.1.3.100.1.19.11
		tacacsAccountingTable OBJECT-TYPE
			SYNTAX SEQUENCE OF TacacsAccountingEntry
			MAX-ACCESS not-accessible
			STATUS current
			DESCRIPTION
				"Description."
			::= { aaaManagementObjects 11 }

		
		-- 1.3.6.1.4.1.34592.1.3.100.1.19.11.1
		tacacsAccountingEntry OBJECT-TYPE
			SYNTAX TacacsAccountingEntry
			MAX-ACCESS not-accessible
			STATUS current
			DESCRIPTION
				"Description."
			INDEX { tacacsAccountingIndex }
			::= { tacacsAccountingTable 1 }

		
		TacacsAccountingEntry ::=
			SEQUENCE { 
				tacacsAccountingIndex
					Integer32,
				tacacsAccountingIp
					IpAddress,
				tacacsAccountingShareKey
					DisplayString,
				tacacsAccountingPort
					Integer32,
				tacacsAccountingRowStatus
					RowStatus
			 }

		-- 1.3.6.1.4.1.34592.1.3.100.1.19.11.1.1
		tacacsAccountingIndex OBJECT-TYPE
			SYNTAX Integer32
			MAX-ACCESS not-accessible
			STATUS current
			DESCRIPTION
				"Description."
			::= { tacacsAccountingEntry 1 }

		
		-- 1.3.6.1.4.1.34592.1.3.100.1.19.11.1.2
		tacacsAccountingIp OBJECT-TYPE
			SYNTAX IpAddress
			MAX-ACCESS read-write
			STATUS current
			DESCRIPTION
				"Description."
			::= { tacacsAccountingEntry 2 }

		
		-- 1.3.6.1.4.1.34592.1.3.100.1.19.11.1.3
		tacacsAccountingShareKey OBJECT-TYPE
			SYNTAX DisplayString
			MAX-ACCESS read-write
			STATUS current
			DESCRIPTION
				"Description."
			::= { tacacsAccountingEntry 3 }

		
		-- 1.3.6.1.4.1.34592.1.3.100.1.19.11.1.4
		tacacsAccountingPort OBJECT-TYPE
			SYNTAX Integer32
			MAX-ACCESS read-write
			STATUS current
			DESCRIPTION
				"Description."
			::= { tacacsAccountingEntry 4 }

		
		-- 1.3.6.1.4.1.34592.1.3.100.1.19.11.1.5
		tacacsAccountingRowStatus OBJECT-TYPE
			SYNTAX RowStatus
				{
				active(1),
				notInService(2),
				notReady(3),
				createAndGo(4),
				createAndWait(5),
				destroy(6)
				}
			MAX-ACCESS read-create
			STATUS current
			DESCRIPTION
				"Description."
			::= { tacacsAccountingEntry 5 }

		
		-- 1.3.6.1.4.1.34592.1.3.100.2
		sniObjects OBJECT IDENTIFIER ::= { nscrtvPonTreeExt 2 }

		
		-- 1.3.6.1.4.1.34592.1.3.100.2.1
		sniAttributeExtTable OBJECT-TYPE
			SYNTAX SEQUENCE OF SniAttributeExtEntry
			MAX-ACCESS not-accessible
			STATUS current
			DESCRIPTION
				"Description."
			::= { sniObjects 1 }

		
		-- 1.3.6.1.4.1.34592.1.3.100.2.1.1
		sniAttributeExtEntry OBJECT-TYPE
			SYNTAX SniAttributeExtEntry
			MAX-ACCESS not-accessible
			STATUS current
			DESCRIPTION
				"Description."
			INDEX { sniAttributeExtDeviceIndex, sniAttributeExtCardIndex, sniAttributeExtPortIndex }
			::= { sniAttributeExtTable 1 }

		
		SniAttributeExtEntry ::=
			SEQUENCE { 
				sniAttributeExtDeviceIndex
					NscrtvPonExtDeviceIndex,
				sniAttributeExtCardIndex
					NscrtvPonExtCardIndex,
				sniAttributeExtPortIndex
					NscrtvPonPortIndex,
				sniFlowControlEnable
					TruthValue,
				sniMaxTransmissionUnit
					Unsigned32,
				sniMaxFrameSize
					Unsigned32,
				sniMacLearnEnable
					TruthValue,
				sniMediaTypeActive
					INTEGER
			 }

		-- 1.3.6.1.4.1.34592.1.3.100.2.1.1.1
		sniAttributeExtDeviceIndex OBJECT-TYPE
			SYNTAX NscrtvPonExtDeviceIndex
			MAX-ACCESS not-accessible
			STATUS current
			DESCRIPTION
				"Description."
			::= { sniAttributeExtEntry 1 }

		
		-- 1.3.6.1.4.1.34592.1.3.100.2.1.1.2
		sniAttributeExtCardIndex OBJECT-TYPE
			SYNTAX NscrtvPonExtCardIndex
			MAX-ACCESS not-accessible
			STATUS current
			DESCRIPTION
				"Description."
			::= { sniAttributeExtEntry 2 }

		
		-- 1.3.6.1.4.1.34592.1.3.100.2.1.1.3
		sniAttributeExtPortIndex OBJECT-TYPE
			SYNTAX NscrtvPonPortIndex
			MAX-ACCESS not-accessible
			STATUS current
			DESCRIPTION
				"Description."
			::= { sniAttributeExtEntry 3 }

		
		-- 1.3.6.1.4.1.34592.1.3.100.2.1.1.4
		sniFlowControlEnable OBJECT-TYPE
			SYNTAX TruthValue
			MAX-ACCESS read-write
			STATUS current
			DESCRIPTION
				"Description."
			::= { sniAttributeExtEntry 4 }

		
		-- 1.3.6.1.4.1.34592.1.3.100.2.1.1.5
		sniMaxTransmissionUnit OBJECT-TYPE
			SYNTAX Unsigned32
			MAX-ACCESS read-write
			STATUS current
			DESCRIPTION
				"Description."
			::= { sniAttributeExtEntry 5 }

		
		-- 1.3.6.1.4.1.34592.1.3.100.2.1.1.6
		sniMaxFrameSize OBJECT-TYPE
			SYNTAX Unsigned32
			MAX-ACCESS read-write
			STATUS current
			DESCRIPTION
				"Description."
			::= { sniAttributeExtEntry 6 }

		
		-- 1.3.6.1.4.1.34592.1.3.100.2.1.1.7
		sniMacLearnEnable OBJECT-TYPE
			SYNTAX TruthValue
			MAX-ACCESS read-write
			STATUS current
			DESCRIPTION
				"Description."
			::= { sniAttributeExtEntry 7 }

		
		-- 1.3.6.1.4.1.34592.1.3.100.2.1.1.8
		sniMediaTypeActive OBJECT-TYPE
			SYNTAX INTEGER
				{
				none(0),
				copper(1),
				fiber(2)
				}
			MAX-ACCESS read-only
			STATUS current
			DESCRIPTION
				"Description."
			::= { sniAttributeExtEntry 8 }

		
		-- 1.3.6.1.4.1.34592.1.3.100.2.2
		sniPortOpticalTransmissionPropertyTable OBJECT-TYPE
			SYNTAX SEQUENCE OF SniPortOpticalTransmissionPropertyEntry
			MAX-ACCESS not-accessible
			STATUS current
			DESCRIPTION
				"Description."
			::= { sniObjects 2 }

		
		-- 1.3.6.1.4.1.34592.1.3.100.2.2.1
		sniPortOpticalTransmissionPropertyEntry OBJECT-TYPE
			SYNTAX SniPortOpticalTransmissionPropertyEntry
			MAX-ACCESS not-accessible
			STATUS current
			DESCRIPTION
				"Description."
			INDEX { sniOpDeviceIndex, sniOpCardIndex, sniOpPortIndex }
			::= { sniPortOpticalTransmissionPropertyTable 1 }

		
		SniPortOpticalTransmissionPropertyEntry ::=
			SEQUENCE { 
				sniOpDeviceIndex
					NscrtvPonExtDeviceIndex,
				sniOpCardIndex
					NscrtvPonExtCardIndex,
				sniOpPortIndex
					NscrtvPonPortIndex,
				sniOpTemperature
					Integer32,
				sniOpVcc
					Unsigned32,
				sniOpBias
					Unsigned32,
				sniOpTxPower
					Integer32,
				sniOpRxPower
					Integer32
			 }

		-- 1.3.6.1.4.1.34592.1.3.100.2.2.1.1
		sniOpDeviceIndex OBJECT-TYPE
			SYNTAX NscrtvPonExtDeviceIndex
			MAX-ACCESS not-accessible
			STATUS current
			DESCRIPTION
				"Description."
			::= { sniPortOpticalTransmissionPropertyEntry 1 }

		
		-- 1.3.6.1.4.1.34592.1.3.100.2.2.1.2
		sniOpCardIndex OBJECT-TYPE
			SYNTAX NscrtvPonExtCardIndex
			MAX-ACCESS not-accessible
			STATUS current
			DESCRIPTION
				"Description."
			::= { sniPortOpticalTransmissionPropertyEntry 2 }

		
		-- 1.3.6.1.4.1.34592.1.3.100.2.2.1.3
		sniOpPortIndex OBJECT-TYPE
			SYNTAX NscrtvPonPortIndex
			MAX-ACCESS not-accessible
			STATUS current
			DESCRIPTION
				"Description."
			::= { sniPortOpticalTransmissionPropertyEntry 3 }

		
		-- 1.3.6.1.4.1.34592.1.3.100.2.2.1.4
		sniOpTemperature OBJECT-TYPE
			SYNTAX Integer32
			UNITS "Centi-degree centigrade"
			MAX-ACCESS read-only
			STATUS current
			DESCRIPTION
				"Description."
			::= { sniPortOpticalTransmissionPropertyEntry 4 }

		
		-- 1.3.6.1.4.1.34592.1.3.100.2.2.1.5
		sniOpVcc OBJECT-TYPE
			SYNTAX Unsigned32
			UNITS "centi-mV"
			MAX-ACCESS read-only
			STATUS current
			DESCRIPTION
				"Description."
			::= { sniPortOpticalTransmissionPropertyEntry 5 }

		
		-- 1.3.6.1.4.1.34592.1.3.100.2.2.1.6
		sniOpBias OBJECT-TYPE
			SYNTAX Unsigned32
			UNITS "centi-mA"
			MAX-ACCESS read-only
			STATUS current
			DESCRIPTION
				"Description."
			::= { sniPortOpticalTransmissionPropertyEntry 6 }

		
		-- 1.3.6.1.4.1.34592.1.3.100.2.2.1.7
		sniOpTxPower OBJECT-TYPE
			SYNTAX Integer32
			UNITS "centi-dBm"
			MAX-ACCESS read-only
			STATUS current
			DESCRIPTION
				"Description."
			::= { sniPortOpticalTransmissionPropertyEntry 7 }

		
		-- 1.3.6.1.4.1.34592.1.3.100.2.2.1.8
		sniOpRxPower OBJECT-TYPE
			SYNTAX Integer32
			UNITS "centi-dBm"
			MAX-ACCESS read-only
			STATUS current
			DESCRIPTION
				"Description."
			::= { sniPortOpticalTransmissionPropertyEntry 8 }

		
		-- 1.3.6.1.4.1.34592.1.3.100.2.3
		sniPortRateLimitTable OBJECT-TYPE
			SYNTAX SEQUENCE OF SniPortRateLimitEntry
			MAX-ACCESS not-accessible
			STATUS current
			DESCRIPTION
				"Description."
			::= { sniObjects 3 }

		
		-- 1.3.6.1.4.1.34592.1.3.100.2.3.1
		sniPortRateLimitEntry OBJECT-TYPE
			SYNTAX SniPortRateLimitEntry
			MAX-ACCESS not-accessible
			STATUS current
			DESCRIPTION
				"Description."
			INDEX { sniPortRateLimitDeviceIndex, sniPortRateLimitCardIndex, sniPortRateLimitPortIndex }
			::= { sniPortRateLimitTable 1 }

		
		SniPortRateLimitEntry ::=
			SEQUENCE { 
				sniPortRateLimitDeviceIndex
					NscrtvPonExtDeviceIndex,
				sniPortRateLimitCardIndex
					NscrtvPonExtCardIndex,
				sniPortRateLimitPortIndex
					NscrtvPonPortIndex,
				sniPortInRate
					Unsigned32,
				sniPortOutRate
					Unsigned32,
				sniPortInRateLimitEnable
					TruthValue,
				sniPortOutRateLimitEnable
					TruthValue
			 }

		-- 1.3.6.1.4.1.34592.1.3.100.2.3.1.1
		sniPortRateLimitDeviceIndex OBJECT-TYPE
			SYNTAX NscrtvPonExtDeviceIndex
			MAX-ACCESS not-accessible
			STATUS current
			DESCRIPTION
				"Description."
			::= { sniPortRateLimitEntry 1 }

		
		-- 1.3.6.1.4.1.34592.1.3.100.2.3.1.2
		sniPortRateLimitCardIndex OBJECT-TYPE
			SYNTAX NscrtvPonExtCardIndex
			MAX-ACCESS not-accessible
			STATUS current
			DESCRIPTION
				"Description."
			::= { sniPortRateLimitEntry 2 }

		
		-- 1.3.6.1.4.1.34592.1.3.100.2.3.1.3
		sniPortRateLimitPortIndex OBJECT-TYPE
			SYNTAX NscrtvPonPortIndex
			MAX-ACCESS not-accessible
			STATUS current
			DESCRIPTION
				"Description."
			::= { sniPortRateLimitEntry 3 }

		
		-- 1.3.6.1.4.1.34592.1.3.100.2.3.1.4
		sniPortInRate OBJECT-TYPE
			SYNTAX Unsigned32
			UNITS "kbps"
			MAX-ACCESS read-write
			STATUS current
			DESCRIPTION
				"Description."
			::= { sniPortRateLimitEntry 4 }

		
		-- 1.3.6.1.4.1.34592.1.3.100.2.3.1.5
		sniPortOutRate OBJECT-TYPE
			SYNTAX Unsigned32
			UNITS "kbps"
			MAX-ACCESS read-write
			STATUS current
			DESCRIPTION
				"Description."
			::= { sniPortRateLimitEntry 5 }

		
		-- 1.3.6.1.4.1.34592.1.3.100.2.3.1.6
		sniPortInRateLimitEnable OBJECT-TYPE
			SYNTAX TruthValue
			MAX-ACCESS read-write
			STATUS current
			DESCRIPTION
				"Description."
			::= { sniPortRateLimitEntry 6 }

		
		-- 1.3.6.1.4.1.34592.1.3.100.2.3.1.7
		sniPortOutRateLimitEnable OBJECT-TYPE
			SYNTAX TruthValue
			MAX-ACCESS read-write
			STATUS current
			DESCRIPTION
				"Description."
			::= { sniPortRateLimitEntry 7 }

		
		-- 1.3.6.1.4.1.34592.1.3.100.2.4
		sniMacAddressExtTable OBJECT-TYPE
			SYNTAX SEQUENCE OF SniMacAddressExtEntry
			MAX-ACCESS not-accessible
			STATUS current
			DESCRIPTION
				" "
			::= { sniObjects 4 }

		
		-- 1.3.6.1.4.1.34592.1.3.100.2.4.1
		sniMacAddressExtEntry OBJECT-TYPE
			SYNTAX SniMacAddressExtEntry
			MAX-ACCESS not-accessible
			STATUS current
			DESCRIPTION
				" "
			INDEX { sniMacAddrExtIndex, sniMacAddrExtVlanIdIndex }
			::= { sniMacAddressExtTable 1 }

		
		SniMacAddressExtEntry ::=
			SEQUENCE { 
				sniMacAddrExtIndex
					MacAddress,
				sniMacAddrExtVlanIdIndex
					INTEGER,
				sniMacAddrExtType
					INTEGER,
				sniMacAddrExtSport
					Integer32,
				sniMacAddrExtPortId
					EponDeviceIndex,
				sniMacAddrExtOnuId
					Integer32,
				sniMacAddrExtGemId
					Integer32
			 }

		-- 1.3.6.1.4.1.34592.1.3.100.2.4.1.1
		sniMacAddrExtIndex OBJECT-TYPE
			SYNTAX MacAddress
			MAX-ACCESS not-accessible
			STATUS current
			DESCRIPTION
				" "
			::= { sniMacAddressExtEntry 1 }

		
		-- 1.3.6.1.4.1.34592.1.3.100.2.4.1.2
		sniMacAddrExtVlanIdIndex OBJECT-TYPE
			SYNTAX INTEGER
			MAX-ACCESS not-accessible
			STATUS current
			DESCRIPTION
				" "
			::= { sniMacAddressExtEntry 2 }

		
		-- 1.3.6.1.4.1.34592.1.3.100.2.4.1.3
		sniMacAddrExtType OBJECT-TYPE
			SYNTAX INTEGER
				{
				static(1),
				dynamic(2),
				blackhole(3)
				}
			MAX-ACCESS read-only
			STATUS current
			DESCRIPTION
				" "
			::= { sniMacAddressExtEntry 3 }

		
		-- 1.3.6.1.4.1.34592.1.3.100.2.4.1.4
		sniMacAddrExtSport OBJECT-TYPE
			SYNTAX Integer32
			MAX-ACCESS read-only
			STATUS current
			DESCRIPTION
				" "
			::= { sniMacAddressExtEntry 4 }

		
		-- 1.3.6.1.4.1.34592.1.3.100.2.4.1.5
		sniMacAddrExtPortId OBJECT-TYPE
			SYNTAX EponDeviceIndex
			MAX-ACCESS read-only
			STATUS current
			DESCRIPTION
				" "
			::= { sniMacAddressExtEntry 5 }

		
		-- 1.3.6.1.4.1.34592.1.3.100.2.4.1.6
		sniMacAddrExtOnuId OBJECT-TYPE
			SYNTAX Integer32
			MAX-ACCESS read-only
			STATUS current
			DESCRIPTION
				" "
			::= { sniMacAddressExtEntry 6 }

		
		-- 1.3.6.1.4.1.34592.1.3.100.2.4.1.7
		sniMacAddrExtGemId OBJECT-TYPE
			SYNTAX Integer32
			MAX-ACCESS read-only
			STATUS current
			DESCRIPTION
				" "
			::= { sniMacAddressExtEntry 7 }

		
		-- 1.3.6.1.4.1.34592.1.3.100.2.5
		sniMacAddressCollectTable OBJECT-TYPE
			SYNTAX SEQUENCE OF SniMacAddressCollectEntry
			MAX-ACCESS not-accessible
			STATUS current
			DESCRIPTION
				"Description."
			::= { sniObjects 5 }

		
		-- 1.3.6.1.4.1.34592.1.3.100.2.5.1
		sniMacAddressCollectEntry OBJECT-TYPE
			SYNTAX SniMacAddressCollectEntry
			MAX-ACCESS not-accessible
			STATUS current
			DESCRIPTION
				"Description."
			INDEX { sniMacCollectIndex }
			::= { sniMacAddressCollectTable 1 }

		
		SniMacAddressCollectEntry ::=
			SEQUENCE { 
				sniMacCollectIndex
					Integer32,
				sniMacAddressCollectInfo
					OCTET STRING
			 }

		-- 1.3.6.1.4.1.34592.1.3.100.2.5.1.1
		sniMacCollectIndex OBJECT-TYPE
			SYNTAX Integer32
			MAX-ACCESS not-accessible
			STATUS current
			DESCRIPTION
				"Description."
			::= { sniMacAddressCollectEntry 1 }

		
		-- 1.3.6.1.4.1.34592.1.3.100.2.5.1.2
		sniMacAddressCollectInfo OBJECT-TYPE
			SYNTAX OCTET STRING
			MAX-ACCESS read-only
			STATUS current
			DESCRIPTION
				"Description."
			::= { sniMacAddressCollectEntry 2 }

		
		-- 1.3.6.1.4.1.34592.1.3.100.3
		ponPortObjects OBJECT IDENTIFIER ::= { nscrtvPonTreeExt 3 }

		
		-- 1.3.6.1.4.1.34592.1.3.100.3.1
		ponPortInfoExtTable OBJECT-TYPE
			SYNTAX SEQUENCE OF PonPortInfoExtEntry
			MAX-ACCESS not-accessible
			STATUS current
			DESCRIPTION
				"Description."
			::= { ponPortObjects 1 }

		
		-- 1.3.6.1.4.1.34592.1.3.100.3.1.1
		ponPortInfoExtEntry OBJECT-TYPE
			SYNTAX PonPortInfoExtEntry
			MAX-ACCESS not-accessible
			STATUS current
			DESCRIPTION
				"Description."
			INDEX { ponInfoExtDeviceIndex, ponInfoExtCardIndex, ponInfoExtPortIndex }
			::= { ponPortInfoExtTable 1 }

		
		PonPortInfoExtEntry ::=
			SEQUENCE { 
				ponInfoExtDeviceIndex
					NscrtvPonExtDeviceIndex,
				ponInfoExtCardIndex
					NscrtvPonExtCardIndex,
				ponInfoExtPortIndex
					NscrtvPonPortIndex,
				ponFlowControlEnable
					TruthValue,
				ponMaxTransmissionUnit
					Unsigned32,
				ponMaxFrameSize
					Unsigned32,
				ponMacLearnEnable
					TruthValue,
				ponPortInfoExtLinkUpTime
					DateAndTime,
				ponPortInfoExtLinkDownTime
					DateAndTime,
				ponP2pEnable
					INTEGER,
				ponRougeOnuAutoIsolateSwitch
					INTEGER,
				ponPortInfoOpticalAlarmProfile
					Integer32,
				ponPortInfoExtLongEmitManualDetect
					INTEGER
			 }

		-- 1.3.6.1.4.1.34592.1.3.100.3.1.1.1
		ponInfoExtDeviceIndex OBJECT-TYPE
			SYNTAX NscrtvPonExtDeviceIndex
			MAX-ACCESS not-accessible
			STATUS current
			DESCRIPTION
				"Description."
			::= { ponPortInfoExtEntry 1 }

		
		-- 1.3.6.1.4.1.34592.1.3.100.3.1.1.2
		ponInfoExtCardIndex OBJECT-TYPE
			SYNTAX NscrtvPonExtCardIndex
			MAX-ACCESS not-accessible
			STATUS current
			DESCRIPTION
				"Description."
			::= { ponPortInfoExtEntry 2 }

		
		-- 1.3.6.1.4.1.34592.1.3.100.3.1.1.3
		ponInfoExtPortIndex OBJECT-TYPE
			SYNTAX NscrtvPonPortIndex
			MAX-ACCESS not-accessible
			STATUS current
			DESCRIPTION
				"Description."
			::= { ponPortInfoExtEntry 3 }

		
		-- 1.3.6.1.4.1.34592.1.3.100.3.1.1.4
		ponFlowControlEnable OBJECT-TYPE
			SYNTAX TruthValue
			MAX-ACCESS read-write
			STATUS current
			DESCRIPTION
				"Description."
			::= { ponPortInfoExtEntry 4 }

		
		-- 1.3.6.1.4.1.34592.1.3.100.3.1.1.5
		ponMaxTransmissionUnit OBJECT-TYPE
			SYNTAX Unsigned32
			MAX-ACCESS read-write
			STATUS current
			DESCRIPTION
				"Description."
			::= { ponPortInfoExtEntry 5 }

		
		-- 1.3.6.1.4.1.34592.1.3.100.3.1.1.6
		ponMaxFrameSize OBJECT-TYPE
			SYNTAX Unsigned32
			MAX-ACCESS read-write
			STATUS current
			DESCRIPTION
				"Description."
			::= { ponPortInfoExtEntry 6 }

		
		-- 1.3.6.1.4.1.34592.1.3.100.3.1.1.7
		ponMacLearnEnable OBJECT-TYPE
			SYNTAX TruthValue
			MAX-ACCESS read-write
			STATUS current
			DESCRIPTION
				"Description."
			::= { ponPortInfoExtEntry 7 }

		
		-- 1.3.6.1.4.1.34592.1.3.100.3.1.1.8
		ponPortInfoExtLinkUpTime OBJECT-TYPE
			SYNTAX DateAndTime
			MAX-ACCESS read-only
			STATUS current
			DESCRIPTION
				"Description."
			::= { ponPortInfoExtEntry 8 }

		
		-- 1.3.6.1.4.1.34592.1.3.100.3.1.1.9
		ponPortInfoExtLinkDownTime OBJECT-TYPE
			SYNTAX DateAndTime
			MAX-ACCESS read-only
			STATUS current
			DESCRIPTION
				"Description."
			::= { ponPortInfoExtEntry 9 }

		
		-- 1.3.6.1.4.1.34592.1.3.100.3.1.1.10
		ponP2pEnable OBJECT-TYPE
			SYNTAX INTEGER
				{
				disable(0),
				enable(1)
				}
			MAX-ACCESS read-write
			STATUS current
			DESCRIPTION
				"Description."
			::= { ponPortInfoExtEntry 10 }

		
		-- 1.3.6.1.4.1.34592.1.3.100.3.1.1.11
		ponRougeOnuAutoIsolateSwitch OBJECT-TYPE
			SYNTAX INTEGER
				{
				disable(0),
				enable(1)
				}
			MAX-ACCESS read-write
			STATUS current
			DESCRIPTION
				"Description."
			::= { ponPortInfoExtEntry 11 }

		
		-- 1.3.6.1.4.1.34592.1.3.100.3.1.1.12
		ponPortInfoOpticalAlarmProfile OBJECT-TYPE
			SYNTAX Integer32
			MAX-ACCESS read-write
			STATUS current
			DESCRIPTION
				"Description."
			::= { ponPortInfoExtEntry 12 }

		
		-- 1.3.6.1.4.1.34592.1.3.100.3.1.1.13
		ponPortInfoExtLongEmitManualDetect OBJECT-TYPE
			SYNTAX INTEGER
			MAX-ACCESS read-write
			STATUS current
			DESCRIPTION
				"Description."
			::= { ponPortInfoExtEntry 13 }

		
		-- 1.3.6.1.4.1.34592.1.3.100.3.2
		ponPortRateLimitTable OBJECT-TYPE
			SYNTAX SEQUENCE OF PonPortRateLimitEntry
			MAX-ACCESS not-accessible
			STATUS current
			DESCRIPTION
				"Description."
			::= { ponPortObjects 2 }

		
		-- 1.3.6.1.4.1.34592.1.3.100.3.2.1
		ponPortRateLimitEntry OBJECT-TYPE
			SYNTAX PonPortRateLimitEntry
			MAX-ACCESS not-accessible
			STATUS current
			DESCRIPTION
				"Description."
			INDEX { ponPortRateLimitDeviceIndex, ponPortRateLimitCardIndex, ponPortRateLimitPortIndex }
			::= { ponPortRateLimitTable 1 }

		
		PonPortRateLimitEntry ::=
			SEQUENCE { 
				ponPortRateLimitDeviceIndex
					NscrtvPonExtDeviceIndex,
				ponPortRateLimitCardIndex
					NscrtvPonExtCardIndex,
				ponPortRateLimitPortIndex
					NscrtvPonPortIndex,
				ponPortInRate
					Unsigned32,
				ponPortOutRate
					Unsigned32,
				ponPortInRateLimitEnable
					TruthValue,
				ponPortOutRateLimitEnable
					TruthValue
			 }

		-- 1.3.6.1.4.1.34592.1.3.100.3.2.1.1
		ponPortRateLimitDeviceIndex OBJECT-TYPE
			SYNTAX NscrtvPonExtDeviceIndex
			MAX-ACCESS not-accessible
			STATUS current
			DESCRIPTION
				"Description."
			::= { ponPortRateLimitEntry 1 }

		
		-- 1.3.6.1.4.1.34592.1.3.100.3.2.1.2
		ponPortRateLimitCardIndex OBJECT-TYPE
			SYNTAX NscrtvPonExtCardIndex
			MAX-ACCESS not-accessible
			STATUS current
			DESCRIPTION
				"Description."
			::= { ponPortRateLimitEntry 2 }

		
		-- 1.3.6.1.4.1.34592.1.3.100.3.2.1.3
		ponPortRateLimitPortIndex OBJECT-TYPE
			SYNTAX NscrtvPonPortIndex
			MAX-ACCESS not-accessible
			STATUS current
			DESCRIPTION
				"Description."
			::= { ponPortRateLimitEntry 3 }

		
		-- 1.3.6.1.4.1.34592.1.3.100.3.2.1.4
		ponPortInRate OBJECT-TYPE
			SYNTAX Unsigned32
			UNITS "kbps"
			MAX-ACCESS read-write
			STATUS current
			DESCRIPTION
				"Description."
			::= { ponPortRateLimitEntry 4 }

		
		-- 1.3.6.1.4.1.34592.1.3.100.3.2.1.5
		ponPortOutRate OBJECT-TYPE
			SYNTAX Unsigned32
			UNITS "kbps"
			MAX-ACCESS read-write
			STATUS current
			DESCRIPTION
				"Description."
			::= { ponPortRateLimitEntry 5 }

		
		-- 1.3.6.1.4.1.34592.1.3.100.3.2.1.6
		ponPortInRateLimitEnable OBJECT-TYPE
			SYNTAX TruthValue
			MAX-ACCESS read-write
			STATUS current
			DESCRIPTION
				"Description."
			::= { ponPortRateLimitEntry 6 }

		
		-- 1.3.6.1.4.1.34592.1.3.100.3.2.1.7
		ponPortOutRateLimitEnable OBJECT-TYPE
			SYNTAX TruthValue
			MAX-ACCESS read-write
			STATUS current
			DESCRIPTION
				"Description."
			::= { ponPortRateLimitEntry 7 }

		
		-- 1.3.6.1.4.1.34592.1.3.100.4
		vlanManagementObjects OBJECT IDENTIFIER ::= { nscrtvPonTreeExt 4 }

		
		-- 1.3.6.1.4.1.34592.1.3.100.4.1
		macVlanTable OBJECT-TYPE
			SYNTAX SEQUENCE OF MacVlanEntry
			MAX-ACCESS not-accessible
			STATUS current
			DESCRIPTION
				"Description."
			::= { vlanManagementObjects 1 }

		
		-- 1.3.6.1.4.1.34592.1.3.100.4.1.1
		macVlanEntry OBJECT-TYPE
			SYNTAX MacVlanEntry
			MAX-ACCESS not-accessible
			STATUS current
			DESCRIPTION
				"Description."
			INDEX { macVlanMacAddrIndex }
			::= { macVlanTable 1 }

		
		MacVlanEntry ::=
			SEQUENCE { 
				macVlanMacAddrIndex
					MacAddress,
				macVlanVid
					Unsigned32,
				macVlanPriority
					Unsigned32,
				macVlanRowStatus
					RowStatus
			 }

		-- 1.3.6.1.4.1.34592.1.3.100.4.1.1.1
		macVlanMacAddrIndex OBJECT-TYPE
			SYNTAX MacAddress
			MAX-ACCESS not-accessible
			STATUS current
			DESCRIPTION
				"Description."
			::= { macVlanEntry 1 }

		
		-- 1.3.6.1.4.1.34592.1.3.100.4.1.1.2
		macVlanVid OBJECT-TYPE
			SYNTAX Unsigned32 (0..4095)
			MAX-ACCESS read-create
			STATUS current
			DESCRIPTION
				"Description."
			::= { macVlanEntry 2 }

		
		-- 1.3.6.1.4.1.34592.1.3.100.4.1.1.3
		macVlanPriority OBJECT-TYPE
			SYNTAX Unsigned32 (0..7)
			MAX-ACCESS read-create
			STATUS current
			DESCRIPTION
				"Description."
			::= { macVlanEntry 3 }

		
		-- 1.3.6.1.4.1.34592.1.3.100.4.1.1.4
		macVlanRowStatus OBJECT-TYPE
			SYNTAX RowStatus
			MAX-ACCESS read-create
			STATUS current
			DESCRIPTION
				"Description."
			::= { macVlanEntry 4 }

		
		-- 1.3.6.1.4.1.34592.1.3.100.4.2
		ipSubnetVlanTable OBJECT-TYPE
			SYNTAX SEQUENCE OF IpSubnetVlanEntry
			MAX-ACCESS not-accessible
			STATUS current
			DESCRIPTION
				"Description."
			::= { vlanManagementObjects 2 }

		
		-- 1.3.6.1.4.1.34592.1.3.100.4.2.1
		ipSubnetVlanEntry OBJECT-TYPE
			SYNTAX IpSubnetVlanEntry
			MAX-ACCESS not-accessible
			STATUS current
			DESCRIPTION
				"Description."
			INDEX { ipSubnetVlanIpAddressIndex, ipSubnetVlanNetMaskIndex }
			::= { ipSubnetVlanTable 1 }

		
		IpSubnetVlanEntry ::=
			SEQUENCE { 
				ipSubnetVlanIpAddressIndex
					IpAddress,
				ipSubnetVlanNetMaskIndex
					IpAddress,
				ipSubnetVlanVid
					Unsigned32,
				ipSubnetVlanPriority
					Unsigned32,
				ipSubnetVlanRowStatus
					RowStatus
			 }

		-- 1.3.6.1.4.1.34592.1.3.100.4.2.1.1
		ipSubnetVlanIpAddressIndex OBJECT-TYPE
			SYNTAX IpAddress
			MAX-ACCESS not-accessible
			STATUS current
			DESCRIPTION
				"Description."
			::= { ipSubnetVlanEntry 1 }

		
		-- 1.3.6.1.4.1.34592.1.3.100.4.2.1.2
		ipSubnetVlanNetMaskIndex OBJECT-TYPE
			SYNTAX IpAddress
			MAX-ACCESS not-accessible
			STATUS current
			DESCRIPTION
				"Description."
			::= { ipSubnetVlanEntry 2 }

		
		-- 1.3.6.1.4.1.34592.1.3.100.4.2.1.3
		ipSubnetVlanVid OBJECT-TYPE
			SYNTAX Unsigned32 (0..4095)
			MAX-ACCESS read-create
			STATUS current
			DESCRIPTION
				"Description."
			::= { ipSubnetVlanEntry 3 }

		
		-- 1.3.6.1.4.1.34592.1.3.100.4.2.1.4
		ipSubnetVlanPriority OBJECT-TYPE
			SYNTAX Unsigned32 (0..7)
			MAX-ACCESS read-create
			STATUS current
			DESCRIPTION
				"Description."
			::= { ipSubnetVlanEntry 4 }

		
		-- 1.3.6.1.4.1.34592.1.3.100.4.2.1.5
		ipSubnetVlanRowStatus OBJECT-TYPE
			SYNTAX RowStatus
			MAX-ACCESS read-create
			STATUS current
			DESCRIPTION
				"Description."
			::= { ipSubnetVlanEntry 5 }

		
		-- 1.3.6.1.4.1.34592.1.3.100.4.3
		protocolVlanManagement OBJECT IDENTIFIER ::= { vlanManagementObjects 3 }

		
		-- 1.3.6.1.4.1.34592.1.3.100.4.3.1
		protocolVlanProfileTable OBJECT-TYPE
			SYNTAX SEQUENCE OF ProtocolVlanProfileEntry
			MAX-ACCESS not-accessible
			STATUS current
			DESCRIPTION
				"Description."
			::= { protocolVlanManagement 1 }

		
		-- 1.3.6.1.4.1.34592.1.3.100.4.3.1.1
		protocolVlanProfileEntry OBJECT-TYPE
			SYNTAX ProtocolVlanProfileEntry
			MAX-ACCESS not-accessible
			STATUS current
			DESCRIPTION
				"Description."
			INDEX { protocolVlanProfileIndex }
			::= { protocolVlanProfileTable 1 }

		
		ProtocolVlanProfileEntry ::=
			SEQUENCE { 
				protocolVlanProfileIndex
					Unsigned32,
				protocolVlanProfileEtherType
					OCTET STRING,
				protocolVlanProfileFrameType
					INTEGER,
				protocolVlanProfileRowStatus
					RowStatus
			 }

		-- 1.3.6.1.4.1.34592.1.3.100.4.3.1.1.1
		protocolVlanProfileIndex OBJECT-TYPE
			SYNTAX Unsigned32 (1..16)
			MAX-ACCESS not-accessible
			STATUS current
			DESCRIPTION
				"Description."
			::= { protocolVlanProfileEntry 1 }

		
		-- 1.3.6.1.4.1.34592.1.3.100.4.3.1.1.2
		protocolVlanProfileEtherType OBJECT-TYPE
			SYNTAX OCTET STRING
			MAX-ACCESS read-create
			STATUS current
			DESCRIPTION
				"Ether type (0x0600-0xffff)."
			::= { protocolVlanProfileEntry 2 }

		
		-- 1.3.6.1.4.1.34592.1.3.100.4.3.1.1.3
		protocolVlanProfileFrameType OBJECT-TYPE
			SYNTAX INTEGER
				{
				ethernetII(1),
				raw(2),
				llc(3),
				snap(4)
				}
			MAX-ACCESS read-create
			STATUS current
			DESCRIPTION
				"Description."
			::= { protocolVlanProfileEntry 3 }

		
		-- 1.3.6.1.4.1.34592.1.3.100.4.3.1.1.4
		protocolVlanProfileRowStatus OBJECT-TYPE
			SYNTAX RowStatus
			MAX-ACCESS read-create
			STATUS current
			DESCRIPTION
				"Description."
			::= { protocolVlanProfileEntry 4 }

		
		-- 1.3.6.1.4.1.34592.1.3.100.4.3.2
		portProtocolVlanTable OBJECT-TYPE
			SYNTAX SEQUENCE OF PortProtocolVlanEntry
			MAX-ACCESS not-accessible
			STATUS current
			DESCRIPTION
				"Description."
			::= { protocolVlanManagement 2 }

		
		-- 1.3.6.1.4.1.34592.1.3.100.4.3.2.1
		portProtocolVlanEntry OBJECT-TYPE
			SYNTAX PortProtocolVlanEntry
			MAX-ACCESS not-accessible
			STATUS current
			DESCRIPTION
				"Description."
			INDEX { portProtocolVlanDeviceIndex, portProtocolVlanCardIndex, portProtocolVlanPortIndex, portProtocolVlanProfileIndex }
			::= { portProtocolVlanTable 1 }

		
		PortProtocolVlanEntry ::=
			SEQUENCE { 
				portProtocolVlanDeviceIndex
					NscrtvPonExtDeviceIndex,
				portProtocolVlanCardIndex
					NscrtvPonExtCardIndex,
				portProtocolVlanPortIndex
					NscrtvPonPortIndex,
				portProtocolVlanProfileIndex
					Unsigned32,
				portProtocolVlanVid
					Unsigned32,
				portProtocolVlanRowStatus
					RowStatus
			 }

		-- 1.3.6.1.4.1.34592.1.3.100.4.3.2.1.1
		portProtocolVlanDeviceIndex OBJECT-TYPE
			SYNTAX NscrtvPonExtDeviceIndex
			MAX-ACCESS not-accessible
			STATUS current
			DESCRIPTION
				"Description."
			::= { portProtocolVlanEntry 1 }

		
		-- 1.3.6.1.4.1.34592.1.3.100.4.3.2.1.2
		portProtocolVlanCardIndex OBJECT-TYPE
			SYNTAX NscrtvPonExtCardIndex
			MAX-ACCESS not-accessible
			STATUS current
			DESCRIPTION
				"Description."
			::= { portProtocolVlanEntry 2 }

		
		-- 1.3.6.1.4.1.34592.1.3.100.4.3.2.1.3
		portProtocolVlanPortIndex OBJECT-TYPE
			SYNTAX NscrtvPonPortIndex
			MAX-ACCESS not-accessible
			STATUS current
			DESCRIPTION
				"Description."
			::= { portProtocolVlanEntry 3 }

		
		-- 1.3.6.1.4.1.34592.1.3.100.4.3.2.1.4
		portProtocolVlanProfileIndex OBJECT-TYPE
			SYNTAX Unsigned32 (1..16)
			MAX-ACCESS not-accessible
			STATUS current
			DESCRIPTION
				"Description."
			::= { portProtocolVlanEntry 4 }

		
		-- 1.3.6.1.4.1.34592.1.3.100.4.3.2.1.5
		portProtocolVlanVid OBJECT-TYPE
			SYNTAX Unsigned32 (0..4095)
			MAX-ACCESS read-create
			STATUS current
			DESCRIPTION
				"Description."
			::= { portProtocolVlanEntry 5 }

		
		-- 1.3.6.1.4.1.34592.1.3.100.4.3.2.1.6
		portProtocolVlanRowStatus OBJECT-TYPE
			SYNTAX RowStatus
			MAX-ACCESS read-create
			STATUS current
			DESCRIPTION
				"Description."
			::= { portProtocolVlanEntry 6 }

		
		-- 1.3.6.1.4.1.34592.1.3.100.4.4
		portVlanHybridTable OBJECT-TYPE
			SYNTAX SEQUENCE OF PortVlanHybridEntry
			MAX-ACCESS not-accessible
			STATUS current
			DESCRIPTION
				"端口Vlan hybrid表(VLAN Hybrid表)
				This table applies on OLT pon port, OLT SNI, OLT onu ID, ONU UNI.
				1. If the table is maintained in OLT device(OLT作为SNMP Agent):
				Applied Obj  - Descriptions of Index
				------------------------------------------------------------------
				OLT Pon Port - OnuNum of pvtDeviceIndex shall be set to 0,
				/OLT SNI     pvtCardIndex, and pvtPortIndex set to 0 indicates
				         meaningless 
				OLT onu ID   - Set pvtDeviceIndex to corresponding ONU ID,
				         pvtCardIndex, and pvtPortIndex set to 0 indicates
				         meaningless        
				ONU UNI    - Set pvtDeviceIndex to corresponding ONU ID,
				         pvtCardIndex, and pvtPortIndex set to the corresponding 
				         value
				
				2. If the table is maintained in ONU device(ONU作为SNMP Agent):
				pvtDeviceIndex shall be set to 0 to indicate meaningless.
				pvtCardIndex shall be set to corresponding slot.
				pvtPortIndex shall be set to corresponding port."
			::= { vlanManagementObjects 4 }

		
		-- 1.3.6.1.4.1.34592.1.3.100.4.4.1
		portVlanHybridEntry OBJECT-TYPE
			SYNTAX PortVlanHybridEntry
			MAX-ACCESS not-accessible
			STATUS current
			DESCRIPTION
				" "
			INDEX { hybridDeviceIndex, hybridCardIndex, hybridPortIndex }
			::= { portVlanHybridTable 1 }

		
		PortVlanHybridEntry ::=
			SEQUENCE { 
				hybridDeviceIndex
					EponDeviceIndex,
				hybridCardIndex
					EponCardIndex,
				hybridPortIndex
					INTEGER,
				hybridVidTaggedList
					OCTET STRING,
				hybridVidUntaggedList
					OCTET STRING,
				portVlanHybridRowStatus
					RowStatus
			 }

		-- 1.3.6.1.4.1.34592.1.3.100.4.4.1.1
		hybridDeviceIndex OBJECT-TYPE
			SYNTAX EponDeviceIndex
			MAX-ACCESS not-accessible
			STATUS current
			DESCRIPTION
				"
				设备索引号。
				"
			::= { portVlanHybridEntry 1 }

		
		-- 1.3.6.1.4.1.34592.1.3.100.4.4.1.2
		hybridCardIndex OBJECT-TYPE
			SYNTAX EponCardIndex
			MAX-ACCESS not-accessible
			STATUS current
			DESCRIPTION
				"
				板卡索引号。"
			::= { portVlanHybridEntry 2 }

		
		-- 1.3.6.1.4.1.34592.1.3.100.4.4.1.3
		hybridPortIndex OBJECT-TYPE
			SYNTAX INTEGER
			MAX-ACCESS not-accessible
			STATUS current
			DESCRIPTION
				"
				端口索引号。
				"
			::= { portVlanHybridEntry 3 }

		
		-- 1.3.6.1.4.1.34592.1.3.100.4.4.1.4
		hybridVidTaggedList OBJECT-TYPE
			SYNTAX OCTET STRING (SIZE (512))
			MAX-ACCESS read-create
			STATUS current
			DESCRIPTION
				"
				Hybrid Vlan Taggged List for the port
				数据行数为端口数量,vlan存储为一个4096位二进制,通过在第n位标记为1,表示vlan n在此端口透传。
				采用类似INTERNET比特顺序,从左到右的OCTET分别为OCTET 0, OCTET 1, ...
				每个OCTET的bit从左到右分别为bit0,bit1,...,bit7。
				按照bit和OCTET由小到大的顺序,每个bit对应于一个VLAN,VLAN ID范围为0..4095。
				第一个bit对应VLAN 0,最后一个bit对应VLAN 4095。
				如果bit置位,表示该包括该VLAN,否则不包括。"
			::= { portVlanHybridEntry 4 }

		
		-- 1.3.6.1.4.1.34592.1.3.100.4.4.1.5
		hybridVidUntaggedList OBJECT-TYPE
			SYNTAX OCTET STRING (SIZE (512))
			MAX-ACCESS read-create
			STATUS current
			DESCRIPTION
				"
				Hybrid Vlan Untaggged List for the port
				数据行数为端口数量,vlan存储为一个4096位二进制,通过在第n位标记为1,表示vlan n在此端口透传。
				采用类似INTERNET比特顺序,从左到右的OCTET分别为OCTET 0, OCTET 1, ...
				每个OCTET的bit从左到右分别为bit0,bit1,...,bit7。
				按照bit和OCTET由小到大的顺序,每个bit对应于一个VLAN,VLAN ID范围为0..4095。
				第一个bit对应VLAN 0,最后一个bit对应VLAN 4095。
				如果bit置位,表示该包括该VLAN,否则不包括。"
			::= { portVlanHybridEntry 5 }

		
		-- 1.3.6.1.4.1.34592.1.3.100.4.4.1.6
		portVlanHybridRowStatus OBJECT-TYPE
			SYNTAX RowStatus
			MAX-ACCESS read-create
			STATUS current
			DESCRIPTION
				"
				行状态"
			::= { portVlanHybridEntry 6 }

		
		-- 1.3.6.1.4.1.34592.1.3.100.4.5
		vlanListSet OBJECT-TYPE
			SYNTAX OCTET STRING
			MAX-ACCESS read-write
			STATUS current
			DESCRIPTION
				"Description."
			::= { vlanManagementObjects 5 }

		
		-- 1.3.6.1.4.1.34592.1.3.100.4.6
		vlanCollectTable OBJECT-TYPE
			SYNTAX SEQUENCE OF VlanCollectEntry
			MAX-ACCESS not-accessible
			STATUS current
			DESCRIPTION
				"Description."
			::= { vlanManagementObjects 6 }

		
		-- 1.3.6.1.4.1.34592.1.3.100.4.6.1
		vlanCollectEntry OBJECT-TYPE
			SYNTAX VlanCollectEntry
			MAX-ACCESS not-accessible
			STATUS current
			DESCRIPTION
				"Description."
			INDEX { vlanCollectIndex }
			::= { vlanCollectTable 1 }

		
		VlanCollectEntry ::=
			SEQUENCE { 
				vlanCollectIndex
					Integer32,
				vlanCollectInformation
					OCTET STRING
			 }

		-- 1.3.6.1.4.1.34592.1.3.100.4.6.1.1
		vlanCollectIndex OBJECT-TYPE
			SYNTAX Integer32
			MAX-ACCESS not-accessible
			STATUS current
			DESCRIPTION
				"Description."
			::= { vlanCollectEntry 1 }

		
		-- 1.3.6.1.4.1.34592.1.3.100.4.6.1.2
		vlanCollectInformation OBJECT-TYPE
			SYNTAX OCTET STRING
			MAX-ACCESS read-only
			STATUS current
			DESCRIPTION
				"Description."
			::= { vlanCollectEntry 2 }

		
		-- 1.3.6.1.4.1.34592.1.3.100.4.7
		vlanTranslateCollectTable OBJECT-TYPE
			SYNTAX SEQUENCE OF VlanTranslateCollectEntry
			MAX-ACCESS not-accessible
			STATUS current
			DESCRIPTION
				"Description."
			::= { vlanManagementObjects 7 }

		
		-- 1.3.6.1.4.1.34592.1.3.100.4.7.1
		vlanTranslateCollectEntry OBJECT-TYPE
			SYNTAX VlanTranslateCollectEntry
			MAX-ACCESS not-accessible
			STATUS current
			DESCRIPTION
				"Description."
			INDEX { vlanTranslateCollectIndex }
			::= { vlanTranslateCollectTable 1 }

		
		VlanTranslateCollectEntry ::=
			SEQUENCE { 
				vlanTranslateCollectIndex
					Integer32,
				vlanTranslateCollectInfo
					OCTET STRING
			 }

		-- 1.3.6.1.4.1.34592.1.3.100.4.7.1.1
		vlanTranslateCollectIndex OBJECT-TYPE
			SYNTAX Integer32
			MAX-ACCESS not-accessible
			STATUS current
			DESCRIPTION
				"Description."
			::= { vlanTranslateCollectEntry 1 }

		
		-- 1.3.6.1.4.1.34592.1.3.100.4.7.1.2
		vlanTranslateCollectInfo OBJECT-TYPE
			SYNTAX OCTET STRING
			MAX-ACCESS read-only
			STATUS current
			DESCRIPTION
				"Description."
			::= { vlanTranslateCollectEntry 2 }

		
		-- 1.3.6.1.4.1.34592.1.3.100.4.8
		vlanUserBridgeObjects OBJECT IDENTIFIER ::= { vlanManagementObjects 8 }

		
		-- 1.3.6.1.4.1.34592.1.3.100.4.8.1
		vlanUserBridgeConfig OBJECT-TYPE
			SYNTAX OCTET STRING
			MAX-ACCESS read-write
			STATUS current
			DESCRIPTION
				"此节点存储为一个4096位二进制,通过在第n位标记为1,表示vlan n使能user bridge功能，
				标记为0，则表示vlan n关闭user bridge功能。
				    采用类似INTERNET比特顺序,从左到右的OCTET分别为OCTET 0, OCTET 1, ...
				    每个OCTET的bit从左到右分别为bit0,bit1,...,bit7。
				    按照bit和OCTET由小到大的顺序,每个bit对应于一个VLAN,VLAN ID范围为0..4095。
				    第一个bit对应VLAN 0,最后一个bit对应VLAN 4095。"
			::= { vlanUserBridgeObjects 1 }

		
		-- 1.3.6.1.4.1.34592.1.3.100.5
		dhcpManagementObjects OBJECT IDENTIFIER ::= { nscrtvPonTreeExt 5 }

		
		-- 1.3.6.1.4.1.34592.1.3.100.5.1
		dhcpSnoopingGlobalSetTable OBJECT-TYPE
			SYNTAX SEQUENCE OF DhcpSnoopingGlobalSetEntry
			MAX-ACCESS not-accessible
			STATUS current
			DESCRIPTION
				"Description."
			::= { dhcpManagementObjects 1 }

		
		-- 1.3.6.1.4.1.34592.1.3.100.5.1.1
		dhcpSnoopingGlobalSetEntry OBJECT-TYPE
			SYNTAX DhcpSnoopingGlobalSetEntry
			MAX-ACCESS not-accessible
			STATUS current
			DESCRIPTION
				"Description."
			INDEX { dhcpSnGlobalSetDeviceIndex }
			::= { dhcpSnoopingGlobalSetTable 1 }

		
		DhcpSnoopingGlobalSetEntry ::=
			SEQUENCE { 
				dhcpSnGlobalSetDeviceIndex
					NscrtvPonExtDeviceIndex,
				dhcpSnGlobalSetEnable
					TruthValue,
				dhcpSnGlobalSetChaddrCheckEnable
					TruthValue,
				dhcpSnGlobalSetVlanList
					OCTET STRING,
				dhcpSnGlobalSetOption82Enable
					TruthValue,
				dhcpSnGlobalSetOption82Policy
					INTEGER,
				dhcpSnGlobalSetOption82Format
					OCTET STRING,
				dhcpSnoopingArpReplyFast
					INTEGER
			 }

		-- 1.3.6.1.4.1.34592.1.3.100.5.1.1.1
		dhcpSnGlobalSetDeviceIndex OBJECT-TYPE
			SYNTAX NscrtvPonExtDeviceIndex
			MAX-ACCESS not-accessible
			STATUS current
			DESCRIPTION
				"Description."
			::= { dhcpSnoopingGlobalSetEntry 1 }

		
		-- 1.3.6.1.4.1.34592.1.3.100.5.1.1.2
		dhcpSnGlobalSetEnable OBJECT-TYPE
			SYNTAX TruthValue
			MAX-ACCESS read-write
			STATUS current
			DESCRIPTION
				"Description."
			::= { dhcpSnoopingGlobalSetEntry 2 }

		
		-- 1.3.6.1.4.1.34592.1.3.100.5.1.1.3
		dhcpSnGlobalSetChaddrCheckEnable OBJECT-TYPE
			SYNTAX TruthValue
			MAX-ACCESS read-write
			STATUS current
			DESCRIPTION
				"Description."
			::= { dhcpSnoopingGlobalSetEntry 3 }

		
		-- 1.3.6.1.4.1.34592.1.3.100.5.1.1.4
		dhcpSnGlobalSetVlanList OBJECT-TYPE
			SYNTAX OCTET STRING (SIZE (512))
			MAX-ACCESS read-write
			STATUS current
			DESCRIPTION
				"        
				采用类似INTERNET比特顺序,从左到右的OCTET分别为OCTET 0, OCTET 1, ...
				每个OCTET的bit从左到右分别为bit0,bit1,...,bit7。
				按照bit和OCTET由小到大的顺序,每个bit对应于一个VLAN,VLAN ID范围为0..4095。
				第一个bit对应VLAN 0,最后一个bit对应VLAN 4095。
				如果bit置位,表示该包括该VLAN,否则不包括。
				"
			::= { dhcpSnoopingGlobalSetEntry 4 }

		
		-- 1.3.6.1.4.1.34592.1.3.100.5.1.1.5
		dhcpSnGlobalSetOption82Enable OBJECT-TYPE
			SYNTAX TruthValue
			MAX-ACCESS read-write
			STATUS current
			DESCRIPTION
				"Description."
			::= { dhcpSnoopingGlobalSetEntry 5 }

		
		-- 1.3.6.1.4.1.34592.1.3.100.5.1.1.6
		dhcpSnGlobalSetOption82Policy OBJECT-TYPE
			SYNTAX INTEGER
				{
				keep(1),
				drop(2),
				replace(3),
				merge(4)
				}
			MAX-ACCESS read-write
			STATUS current
			DESCRIPTION
				"Description."
			::= { dhcpSnoopingGlobalSetEntry 6 }

		
		-- 1.3.6.1.4.1.34592.1.3.100.5.1.1.7
		dhcpSnGlobalSetOption82Format OBJECT-TYPE
			SYNTAX OCTET STRING (SIZE (1..32))
			MAX-ACCESS read-write
			STATUS current
			DESCRIPTION
				"此处显示的是Format的名称，设置时填写的也是Format的名称，
				可通过下表dhcpSnoopingOption82FormatTable查看设备中已有的Format信息。"
			::= { dhcpSnoopingGlobalSetEntry 7 }

		
		-- 1.3.6.1.4.1.34592.1.3.100.5.1.1.8
		dhcpSnoopingArpReplyFast OBJECT-TYPE
			SYNTAX INTEGER
				{
				enable(1),
				disable(2)
				}
			MAX-ACCESS read-write
			STATUS current
			DESCRIPTION
				"Description."
			::= { dhcpSnoopingGlobalSetEntry 8 }

		
		-- 1.3.6.1.4.1.34592.1.3.100.5.2
		dhcpSnoopingPortSetTable OBJECT-TYPE
			SYNTAX SEQUENCE OF DhcpSnoopingPortSetEntry
			MAX-ACCESS not-accessible
			STATUS current
			DESCRIPTION
				"Description."
			::= { dhcpManagementObjects 2 }

		
		-- 1.3.6.1.4.1.34592.1.3.100.5.2.1
		dhcpSnoopingPortSetEntry OBJECT-TYPE
			SYNTAX DhcpSnoopingPortSetEntry
			MAX-ACCESS not-accessible
			STATUS current
			DESCRIPTION
				"Description."
			INDEX { dhcpSnPortSetDeviceIndex, dhcpSnPortSetCardIndex, dhcpSnPortSetPortIndex }
			::= { dhcpSnoopingPortSetTable 1 }

		
		DhcpSnoopingPortSetEntry ::=
			SEQUENCE { 
				dhcpSnPortSetDeviceIndex
					NscrtvPonExtDeviceIndex,
				dhcpSnPortSetCardIndex
					NscrtvPonExtCardIndex,
				dhcpSnPortSetPortIndex
					NscrtvPonPortIndex,
				dhcpSnPortSetTrust
					TruthValue,
				dhcpSnPortSetRequestPktLimitRate
					Unsigned32
			 }

		-- 1.3.6.1.4.1.34592.1.3.100.5.2.1.1
		dhcpSnPortSetDeviceIndex OBJECT-TYPE
			SYNTAX NscrtvPonExtDeviceIndex
			MAX-ACCESS not-accessible
			STATUS current
			DESCRIPTION
				"Description."
			::= { dhcpSnoopingPortSetEntry 1 }

		
		-- 1.3.6.1.4.1.34592.1.3.100.5.2.1.2
		dhcpSnPortSetCardIndex OBJECT-TYPE
			SYNTAX NscrtvPonExtCardIndex
			MAX-ACCESS not-accessible
			STATUS current
			DESCRIPTION
				"Description."
			::= { dhcpSnoopingPortSetEntry 2 }

		
		-- 1.3.6.1.4.1.34592.1.3.100.5.2.1.3
		dhcpSnPortSetPortIndex OBJECT-TYPE
			SYNTAX NscrtvPonPortIndex
			MAX-ACCESS not-accessible
			STATUS current
			DESCRIPTION
				"Description."
			::= { dhcpSnoopingPortSetEntry 3 }

		
		-- 1.3.6.1.4.1.34592.1.3.100.5.2.1.4
		dhcpSnPortSetTrust OBJECT-TYPE
			SYNTAX TruthValue
			MAX-ACCESS read-write
			STATUS current
			DESCRIPTION
				"Description."
			::= { dhcpSnoopingPortSetEntry 4 }

		
		-- 1.3.6.1.4.1.34592.1.3.100.5.2.1.5
		dhcpSnPortSetRequestPktLimitRate OBJECT-TYPE
			SYNTAX Unsigned32 (1..2048)
			UNITS "pps"
			MAX-ACCESS read-write
			STATUS current
			DESCRIPTION
				"Description."
			::= { dhcpSnoopingPortSetEntry 5 }

		
		-- 1.3.6.1.4.1.34592.1.3.100.5.3
		dhcpSnoopingBindManagementTable OBJECT-TYPE
			SYNTAX SEQUENCE OF DhcpSnoopingBindManagementEntry
			MAX-ACCESS not-accessible
			STATUS current
			DESCRIPTION
				"Description."
			::= { dhcpManagementObjects 3 }

		
		-- 1.3.6.1.4.1.34592.1.3.100.5.3.1
		dhcpSnoopingBindManagementEntry OBJECT-TYPE
			SYNTAX DhcpSnoopingBindManagementEntry
			MAX-ACCESS not-accessible
			STATUS current
			DESCRIPTION
				"Description."
			INDEX { dhcpSnBindManagemenDeviceIndex }
			::= { dhcpSnoopingBindManagementTable 1 }

		
		DhcpSnoopingBindManagementEntry ::=
			SEQUENCE { 
				dhcpSnBindManagemenDeviceIndex
					NscrtvPonExtDeviceIndex,
				dhcpSnBindEntryDeleteTime
					Unsigned32,
				dhcpSnBindTableWriteDelay
					Unsigned32,
				dhcpSnBindTableWriteToFlashAction
					TruthValue,
				dhcpSnBindTableSaveToTftpIpAddress
					IpAddress,
				dhcpSnBindTableSaveToTftpAction
					TruthValue,
				dhcpSnBindTableClearByType
					INTEGER,
				dhcpSnBindTableClearByVlan
					Unsigned32,
				dhcpSnBindTableSaveToTftpStatus
					INTEGER,
				dhcpSnBindTableClearByIp
					IpAddress
			 }

		-- 1.3.6.1.4.1.34592.1.3.100.5.3.1.1
		dhcpSnBindManagemenDeviceIndex OBJECT-TYPE
			SYNTAX NscrtvPonExtDeviceIndex
			MAX-ACCESS not-accessible
			STATUS current
			DESCRIPTION
				"Description."
			::= { dhcpSnoopingBindManagementEntry 1 }

		
		-- 1.3.6.1.4.1.34592.1.3.100.5.3.1.2
		dhcpSnBindEntryDeleteTime OBJECT-TYPE
			SYNTAX Unsigned32 (1..86400)
			UNITS "s"
			MAX-ACCESS read-write
			STATUS current
			DESCRIPTION
				"Description."
			::= { dhcpSnoopingBindManagementEntry 2 }

		
		-- 1.3.6.1.4.1.34592.1.3.100.5.3.1.3
		dhcpSnBindTableWriteDelay OBJECT-TYPE
			SYNTAX Unsigned32 (240..86400)
			UNITS "s"
			MAX-ACCESS read-write
			STATUS current
			DESCRIPTION
				"Description."
			::= { dhcpSnoopingBindManagementEntry 3 }

		
		-- 1.3.6.1.4.1.34592.1.3.100.5.3.1.4
		dhcpSnBindTableWriteToFlashAction OBJECT-TYPE
			SYNTAX TruthValue
			MAX-ACCESS read-write
			STATUS current
			DESCRIPTION
				"Description."
			::= { dhcpSnoopingBindManagementEntry 4 }

		
		-- 1.3.6.1.4.1.34592.1.3.100.5.3.1.5
		dhcpSnBindTableSaveToTftpIpAddress OBJECT-TYPE
			SYNTAX IpAddress
			MAX-ACCESS read-write
			STATUS current
			DESCRIPTION
				"Description."
			::= { dhcpSnoopingBindManagementEntry 5 }

		
		-- 1.3.6.1.4.1.34592.1.3.100.5.3.1.6
		dhcpSnBindTableSaveToTftpAction OBJECT-TYPE
			SYNTAX TruthValue
			MAX-ACCESS read-write
			STATUS current
			DESCRIPTION
				"Description."
			::= { dhcpSnoopingBindManagementEntry 6 }

		
		-- 1.3.6.1.4.1.34592.1.3.100.5.3.1.7
		dhcpSnBindTableClearByType OBJECT-TYPE
			SYNTAX INTEGER
				{
				all(1),
				dynamic(2),
				static(3)
				}
			MAX-ACCESS read-write
			STATUS current
			DESCRIPTION
				"Description."
			::= { dhcpSnoopingBindManagementEntry 7 }

		
		-- 1.3.6.1.4.1.34592.1.3.100.5.3.1.8
		dhcpSnBindTableClearByVlan OBJECT-TYPE
			SYNTAX Unsigned32 (0..4095)
			MAX-ACCESS read-write
			STATUS current
			DESCRIPTION
				"Description."
			::= { dhcpSnoopingBindManagementEntry 8 }

		
		-- 1.3.6.1.4.1.34592.1.3.100.5.3.1.9
		dhcpSnBindTableSaveToTftpStatus OBJECT-TYPE
			SYNTAX INTEGER
				{
				idle(1),
				inProgress(2),
				success(3),
				failure(4)
				}
			MAX-ACCESS read-only
			STATUS current
			DESCRIPTION
				"文件传输状态
				idle(1)       - 空闲
				inProgress(2) - 正在传送中
				success(3)    - 传送成功
				failure(4)    - 传送失败"
			::= { dhcpSnoopingBindManagementEntry 9 }

		
		-- 1.3.6.1.4.1.34592.1.3.100.5.3.1.10
		dhcpSnBindTableClearByIp OBJECT-TYPE
			SYNTAX IpAddress
			MAX-ACCESS read-write
			STATUS current
			DESCRIPTION
				"Description."
			::= { dhcpSnoopingBindManagementEntry 10 }

		
		-- 1.3.6.1.4.1.34592.1.3.100.5.4
		dhcpSnoopingBindTable OBJECT-TYPE
			SYNTAX SEQUENCE OF DhcpSnoopingBindEntry
			MAX-ACCESS not-accessible
			STATUS current
			DESCRIPTION
				"Description."
			::= { dhcpManagementObjects 4 }

		
		-- 1.3.6.1.4.1.34592.1.3.100.5.4.1
		dhcpSnoopingBindEntry OBJECT-TYPE
			SYNTAX DhcpSnoopingBindEntry
			MAX-ACCESS not-accessible
			STATUS current
			DESCRIPTION
				"Description."
			INDEX { dhcpSnBindIpAddrIndex, dhcpSnBindVlanIndex }
			::= { dhcpSnoopingBindTable 1 }

		
		DhcpSnoopingBindEntry ::=
			SEQUENCE { 
				dhcpSnBindIpAddrIndex
					IpAddress,
				dhcpSnBindVlanIndex
					Unsigned32,
				dhcpSnBindMacAddress
					MacAddress,
				dhcpSnBindPortId
					NscrtvPonExtDeviceIndex,
				dhcpSnBindType
					INTEGER,
				dhcpSnBindRowStatus
					RowStatus,
				dhcpSnoopingOnuId
					Unsigned32,
				dhcpSnoopingGemId
					Unsigned32,
				dhcpSnoopingLease
					Unsigned32
			 }

		-- 1.3.6.1.4.1.34592.1.3.100.5.4.1.1
		dhcpSnBindIpAddrIndex OBJECT-TYPE
			SYNTAX IpAddress
			MAX-ACCESS not-accessible
			STATUS current
			DESCRIPTION
				"Description."
			::= { dhcpSnoopingBindEntry 1 }

		
		-- 1.3.6.1.4.1.34592.1.3.100.5.4.1.2
		dhcpSnBindVlanIndex OBJECT-TYPE
			SYNTAX Unsigned32 (0..4095)
			MAX-ACCESS not-accessible
			STATUS current
			DESCRIPTION
				"Description."
			::= { dhcpSnoopingBindEntry 2 }

		
		-- 1.3.6.1.4.1.34592.1.3.100.5.4.1.3
		dhcpSnBindMacAddress OBJECT-TYPE
			SYNTAX MacAddress
			MAX-ACCESS read-create
			STATUS current
			DESCRIPTION
				"Description."
			::= { dhcpSnoopingBindEntry 3 }

		
		-- 1.3.6.1.4.1.34592.1.3.100.5.4.1.4
		dhcpSnBindPortId OBJECT-TYPE
			SYNTAX NscrtvPonExtDeviceIndex
			MAX-ACCESS read-create
			STATUS current
			DESCRIPTION
				"Description."
			::= { dhcpSnoopingBindEntry 4 }

		
		-- 1.3.6.1.4.1.34592.1.3.100.5.4.1.5
		dhcpSnBindType OBJECT-TYPE
			SYNTAX INTEGER
				{
				dynamic(1),
				static(2)
				}
			MAX-ACCESS read-create
			STATUS current
			DESCRIPTION
				"Description."
			::= { dhcpSnoopingBindEntry 5 }

		
		-- 1.3.6.1.4.1.34592.1.3.100.5.4.1.6
		dhcpSnBindRowStatus OBJECT-TYPE
			SYNTAX RowStatus
			MAX-ACCESS read-create
			STATUS current
			DESCRIPTION
				"Description."
			::= { dhcpSnoopingBindEntry 6 }

		
		-- 1.3.6.1.4.1.34592.1.3.100.5.4.1.7
		dhcpSnoopingOnuId OBJECT-TYPE
			SYNTAX Unsigned32
			MAX-ACCESS read-only
			STATUS current
			DESCRIPTION
				"Description."
			::= { dhcpSnoopingBindEntry 7 }

		
		-- 1.3.6.1.4.1.34592.1.3.100.5.4.1.8
		dhcpSnoopingGemId OBJECT-TYPE
			SYNTAX Unsigned32
			MAX-ACCESS read-only
			STATUS current
			DESCRIPTION
				"Description."
			::= { dhcpSnoopingBindEntry 8 }

		
		-- 1.3.6.1.4.1.34592.1.3.100.5.4.1.9
		dhcpSnoopingLease OBJECT-TYPE
			SYNTAX Unsigned32
			MAX-ACCESS read-only
			STATUS current
			DESCRIPTION
				"Description."
			::= { dhcpSnoopingBindEntry 9 }

		
		-- 1.3.6.1.4.1.34592.1.3.100.5.5
		dhcpRelayTable OBJECT-TYPE
			SYNTAX SEQUENCE OF DhcpRelayEntry
			MAX-ACCESS not-accessible
			STATUS current
			DESCRIPTION
				"Description."
			::= { dhcpManagementObjects 5 }

		
		-- 1.3.6.1.4.1.34592.1.3.100.5.5.1
		dhcpRelayEntry OBJECT-TYPE
			SYNTAX DhcpRelayEntry
			MAX-ACCESS not-accessible
			STATUS current
			DESCRIPTION
				"Description."
			INDEX { dhcpRelayDeviceIndex }
			::= { dhcpRelayTable 1 }

		
		DhcpRelayEntry ::=
			SEQUENCE { 
				dhcpRelayDeviceIndex
					NscrtvPonExtDeviceIndex,
				dhcpRelayEnable
					TruthValue
			 }

		-- 1.3.6.1.4.1.34592.1.3.100.5.5.1.1
		dhcpRelayDeviceIndex OBJECT-TYPE
			SYNTAX NscrtvPonExtDeviceIndex
			MAX-ACCESS not-accessible
			STATUS current
			DESCRIPTION
				"Description."
			::= { dhcpRelayEntry 1 }

		
		-- 1.3.6.1.4.1.34592.1.3.100.5.5.1.2
		dhcpRelayEnable OBJECT-TYPE
			SYNTAX TruthValue
			MAX-ACCESS read-write
			STATUS current
			DESCRIPTION
				"Description."
			::= { dhcpRelayEntry 2 }

		
		-- 1.3.6.1.4.1.34592.1.3.100.5.6
		dhcpRelayServerConfigTable OBJECT-TYPE
			SYNTAX SEQUENCE OF DhcpRelayServerConfigEntry
			MAX-ACCESS not-accessible
			STATUS current
			DESCRIPTION
				"Description."
			::= { dhcpManagementObjects 6 }

		
		-- 1.3.6.1.4.1.34592.1.3.100.5.6.1
		dhcpRelayServerConfigEntry OBJECT-TYPE
			SYNTAX DhcpRelayServerConfigEntry
			MAX-ACCESS not-accessible
			STATUS current
			DESCRIPTION
				"Description."
			INDEX { dhcpRelayServerConfigDeviceIndex, dhcpRelayVlanIfIndex }
			::= { dhcpRelayServerConfigTable 1 }

		
		DhcpRelayServerConfigEntry ::=
			SEQUENCE { 
				dhcpRelayServerConfigDeviceIndex
					NscrtvPonExtDeviceIndex,
				dhcpRelayVlanIfIndex
					Unsigned32,
				dhcpRelayVlanIfIpAddress
					IpAddress,
				dhcpRelayVlanIfNetmask
					IpAddress,
				dhcpRelayServerIpAddress
					IpAddress,
				dhcpRelayServerConfigRowStatus
					RowStatus
			 }

		-- 1.3.6.1.4.1.34592.1.3.100.5.6.1.1
		dhcpRelayServerConfigDeviceIndex OBJECT-TYPE
			SYNTAX NscrtvPonExtDeviceIndex
			MAX-ACCESS not-accessible
			STATUS current
			DESCRIPTION
				"Description."
			::= { dhcpRelayServerConfigEntry 1 }

		
		-- 1.3.6.1.4.1.34592.1.3.100.5.6.1.2
		dhcpRelayVlanIfIndex OBJECT-TYPE
			SYNTAX Unsigned32 (0..4095)
			MAX-ACCESS read-write
			STATUS current
			DESCRIPTION
				"Description."
			::= { dhcpRelayServerConfigEntry 2 }

		
		-- 1.3.6.1.4.1.34592.1.3.100.5.6.1.3
		dhcpRelayVlanIfIpAddress OBJECT-TYPE
			SYNTAX IpAddress
			MAX-ACCESS read-only
			STATUS current
			DESCRIPTION
				"Description."
			::= { dhcpRelayServerConfigEntry 3 }

		
		-- 1.3.6.1.4.1.34592.1.3.100.5.6.1.4
		dhcpRelayVlanIfNetmask OBJECT-TYPE
			SYNTAX IpAddress
			MAX-ACCESS read-only
			STATUS current
			DESCRIPTION
				"Description."
			::= { dhcpRelayServerConfigEntry 4 }

		
		-- 1.3.6.1.4.1.34592.1.3.100.5.6.1.5
		dhcpRelayServerIpAddress OBJECT-TYPE
			SYNTAX IpAddress
			MAX-ACCESS read-create
			STATUS current
			DESCRIPTION
				"Description."
			::= { dhcpRelayServerConfigEntry 5 }

		
		-- 1.3.6.1.4.1.34592.1.3.100.5.6.1.6
		dhcpRelayServerConfigRowStatus OBJECT-TYPE
			SYNTAX RowStatus
			MAX-ACCESS read-create
			STATUS current
			DESCRIPTION
				"Description."
			::= { dhcpRelayServerConfigEntry 6 }

		
		-- 1.3.6.1.4.1.34592.1.3.100.5.7
		dhcpSnoopingOption82FormatTable OBJECT-TYPE
			SYNTAX SEQUENCE OF DhcpSnoopingOption82FormatEntry
			MAX-ACCESS not-accessible
			STATUS current
			DESCRIPTION
				"dhcp Snooping option82字段格式表"
			::= { dhcpManagementObjects 7 }

		
		-- 1.3.6.1.4.1.34592.1.3.100.5.7.1
		dhcpSnoopingOption82FormatEntry OBJECT-TYPE
			SYNTAX DhcpSnoopingOption82FormatEntry
			MAX-ACCESS not-accessible
			STATUS current
			DESCRIPTION
				"dhcp Snooping option82字段格式表目"
			INDEX { dhcpSnOption82FormatDeviceIndex, dhcpSnOption82FormatIndex }
			::= { dhcpSnoopingOption82FormatTable 1 }

		
		DhcpSnoopingOption82FormatEntry ::=
			SEQUENCE { 
				dhcpSnOption82FormatDeviceIndex
					NscrtvPonExtDeviceIndex,
				dhcpSnOption82FormatIndex
					Unsigned32,
				dhcpSnOption82FormatName
					OCTET STRING,
				dhcpSnOption82FormatType
					INTEGER,
				dhcpSnOption82FormatCircuitId
					OCTET STRING,
				dhcpSnOption82FormatRemoteId
					OCTET STRING,
				dhcpSnOption82FormatRowStatus
					RowStatus
			 }

		-- 1.3.6.1.4.1.34592.1.3.100.5.7.1.1
		dhcpSnOption82FormatDeviceIndex OBJECT-TYPE
			SYNTAX NscrtvPonExtDeviceIndex
			MAX-ACCESS not-accessible
			STATUS current
			DESCRIPTION
				"OLT设备索引号"
			::= { dhcpSnoopingOption82FormatEntry 1 }

		
		-- 1.3.6.1.4.1.34592.1.3.100.5.7.1.2
		dhcpSnOption82FormatIndex OBJECT-TYPE
			SYNTAX Unsigned32 (1..8)
			MAX-ACCESS not-accessible
			STATUS current
			DESCRIPTION
				"dhcp Snooping option82字段格式项索引"
			::= { dhcpSnoopingOption82FormatEntry 2 }

		
		-- 1.3.6.1.4.1.34592.1.3.100.5.7.1.3
		dhcpSnOption82FormatName OBJECT-TYPE
			SYNTAX OCTET STRING (SIZE (1..32))
			MAX-ACCESS read-create
			STATUS current
			DESCRIPTION
				"dhcp Snooping option82字段格式项名称"
			::= { dhcpSnoopingOption82FormatEntry 3 }

		
		-- 1.3.6.1.4.1.34592.1.3.100.5.7.1.4
		dhcpSnOption82FormatType OBJECT-TYPE
			SYNTAX INTEGER
				{
				ascii(1),
				hex(2)
				}
			MAX-ACCESS read-create
			STATUS current
			DESCRIPTION
				"dhcp Snooping option82字段格式项类型"
			::= { dhcpSnoopingOption82FormatEntry 4 }

		
		-- 1.3.6.1.4.1.34592.1.3.100.5.7.1.5
		dhcpSnOption82FormatCircuitId OBJECT-TYPE
			SYNTAX OCTET STRING (SIZE (1..128))
			MAX-ACCESS read-write
			STATUS current
			DESCRIPTION
				"dhcp Snooping option82字段格式项Circuit Id"
			::= { dhcpSnoopingOption82FormatEntry 5 }

		
		-- 1.3.6.1.4.1.34592.1.3.100.5.7.1.6
		dhcpSnOption82FormatRemoteId OBJECT-TYPE
			SYNTAX OCTET STRING (SIZE (1..128))
			MAX-ACCESS read-write
			STATUS current
			DESCRIPTION
				"dhcp Snooping option82字段格式项Remote Id"
			::= { dhcpSnoopingOption82FormatEntry 6 }

		
		-- 1.3.6.1.4.1.34592.1.3.100.5.7.1.7
		dhcpSnOption82FormatRowStatus OBJECT-TYPE
			SYNTAX RowStatus
			MAX-ACCESS read-create
			STATUS current
			DESCRIPTION
				"使用该节点创建表项时，必选参数dhcpSnOption82FormatName、dhcpSnOption82FormatType；
				dhcpSnOption82FormatCircuitId和dhcpSnOption82FormatRemoteId二选一或者同时选择。"
			::= { dhcpSnoopingOption82FormatEntry 7 }

		
		-- 1.3.6.1.4.1.34592.1.3.100.5.8
		dhcpServerObjects OBJECT IDENTIFIER ::= { dhcpManagementObjects 8 }

		
		-- 1.3.6.1.4.1.34592.1.3.100.5.8.1
		dhcpServerEnable OBJECT-TYPE
			SYNTAX RowStatus
				{
				disable(0),
				enable(1)
				}
			MAX-ACCESS read-create
			STATUS current
			DESCRIPTION
				"Description."
			::= { dhcpServerObjects 1 }

		
		-- 1.3.6.1.4.1.34592.1.3.100.5.8.2
		dhcpServerVlanifIndex OBJECT-TYPE
			SYNTAX Unsigned32
			MAX-ACCESS read-only
			STATUS current
			DESCRIPTION
				"Description."
			::= { dhcpServerObjects 2 }

		
		-- 1.3.6.1.4.1.34592.1.3.100.5.8.3
		dhcpServerVlanifId OBJECT-TYPE
			SYNTAX Unsigned32
			MAX-ACCESS read-write
			STATUS current
			DESCRIPTION
				"Description."
			::= { dhcpServerObjects 3 }

		
		-- 1.3.6.1.4.1.34592.1.3.100.5.8.4
		dhcpServerPoolStarIpAddr OBJECT-TYPE
			SYNTAX IpAddress
			MAX-ACCESS read-write
			STATUS current
			DESCRIPTION
				"Description."
			::= { dhcpServerObjects 4 }

		
		-- 1.3.6.1.4.1.34592.1.3.100.5.8.5
		dhcpServerPoolEndIpAddr OBJECT-TYPE
			SYNTAX IpAddress
			MAX-ACCESS read-write
			STATUS current
			DESCRIPTION
				"Description."
			::= { dhcpServerObjects 5 }

		
		-- 1.3.6.1.4.1.34592.1.3.100.5.8.6
		dhcpServerSubNetMask OBJECT-TYPE
			SYNTAX IpAddress
			MAX-ACCESS read-write
			STATUS current
			DESCRIPTION
				"Description."
			::= { dhcpServerObjects 6 }

		
		-- 1.3.6.1.4.1.34592.1.3.100.5.8.7
		dhcpServerGateWay OBJECT-TYPE
			SYNTAX IpAddress
			MAX-ACCESS read-write
			STATUS current
			DESCRIPTION
				"Description."
			::= { dhcpServerObjects 7 }

		
		-- 1.3.6.1.4.1.34592.1.3.100.5.8.8
		dhcpServerDns OBJECT-TYPE
			SYNTAX IpAddress
			MAX-ACCESS read-write
			STATUS current
			DESCRIPTION
				"Description."
			::= { dhcpServerObjects 8 }

		
		-- 1.3.6.1.4.1.34592.1.3.100.5.8.9
		dhcpServerWins OBJECT-TYPE
			SYNTAX IpAddress
			MAX-ACCESS read-write
			STATUS current
			DESCRIPTION
				"Description."
			::= { dhcpServerObjects 9 }

		
		-- 1.3.6.1.4.1.34592.1.3.100.5.8.10
		dhcpServerLeaseTime OBJECT-TYPE
			SYNTAX Unsigned32
			MAX-ACCESS read-write
			STATUS current
			DESCRIPTION
				"Description."
			::= { dhcpServerObjects 10 }

		
		-- 1.3.6.1.4.1.34592.1.3.100.5.8.11
		dhcpServerOption60CheckEnable OBJECT-TYPE
			SYNTAX RowStatus
				{
				disable(0),
				enable(1)
				}
			MAX-ACCESS read-write
			STATUS current
			DESCRIPTION
				"Description."
			::= { dhcpServerObjects 11 }

		
		-- 1.3.6.1.4.1.34592.1.3.100.5.8.12
		dhcpServerOption61CheckEnable OBJECT-TYPE
			SYNTAX RowStatus
				{
				disable(0),
				enable(1)
				}
			MAX-ACCESS read-write
			STATUS current
			DESCRIPTION
				"Description."
			::= { dhcpServerObjects 12 }

		
		-- 1.3.6.1.4.1.34592.1.3.100.5.8.13
		dhcpServerCommit OBJECT-TYPE
			SYNTAX RowStatus
				{
				no-commit(0),
				commit(1)
				}
			MAX-ACCESS read-write
			STATUS current
			DESCRIPTION
				"Description."
			::= { dhcpServerObjects 13 }

		
		-- 1.3.6.1.4.1.34592.1.3.100.5.8.14
		dhcpServerServerName OBJECT-TYPE
			SYNTAX OCTET STRING
			MAX-ACCESS read-write
			STATUS current
			DESCRIPTION
				"Description."
			::= { dhcpServerObjects 14 }

		
		-- 1.3.6.1.4.1.34592.1.3.100.5.9
		dhcpServerPoolTable OBJECT-TYPE
			SYNTAX SEQUENCE OF DhcpServerPoolEntry
			MAX-ACCESS not-accessible
			STATUS current
			DESCRIPTION
				"Description.
				DHCP Server 地址池查看表"
			::= { dhcpManagementObjects 9 }

		
		-- 1.3.6.1.4.1.34592.1.3.100.5.9.1
		dhcpServerPoolEntry OBJECT-TYPE
			SYNTAX DhcpServerPoolEntry
			MAX-ACCESS not-accessible
			STATUS current
			DESCRIPTION
				"Description.
				DHCP Server 地址池查看表目"
			INDEX { dhcpServerPoolIndex }
			::= { dhcpServerPoolTable 1 }

		
		DhcpServerPoolEntry ::=
			SEQUENCE { 
				dhcpServerPoolIndex
					Unsigned32,
				dhcpServerPoolIpAddr
					IpAddress,
				dhcpServerPoolMac
					MacAddress,
				dhcpServerPoolState
					Integer32,
				dhcpServerPoolLeaseTime
					Unsigned32
			 }

		-- 1.3.6.1.4.1.34592.1.3.100.5.9.1.1
		dhcpServerPoolIndex OBJECT-TYPE
			SYNTAX Unsigned32
			MAX-ACCESS read-only
			STATUS current
			DESCRIPTION
				"Description."
			::= { dhcpServerPoolEntry 1 }

		
		-- 1.3.6.1.4.1.34592.1.3.100.5.9.1.2
		dhcpServerPoolIpAddr OBJECT-TYPE
			SYNTAX IpAddress
			MAX-ACCESS read-only
			STATUS current
			DESCRIPTION
				"Description."
			::= { dhcpServerPoolEntry 2 }

		
		-- 1.3.6.1.4.1.34592.1.3.100.5.9.1.3
		dhcpServerPoolMac OBJECT-TYPE
			SYNTAX MacAddress
			MAX-ACCESS read-only
			STATUS current
			DESCRIPTION
				"Description."
			::= { dhcpServerPoolEntry 3 }

		
		-- 1.3.6.1.4.1.34592.1.3.100.5.9.1.4
		dhcpServerPoolState OBJECT-TYPE
			SYNTAX Integer32
			MAX-ACCESS read-only
			STATUS current
			DESCRIPTION
				"Description."
			::= { dhcpServerPoolEntry 4 }

		
		-- 1.3.6.1.4.1.34592.1.3.100.5.9.1.5
		dhcpServerPoolLeaseTime OBJECT-TYPE
			SYNTAX Unsigned32
			MAX-ACCESS read-only
			STATUS current
			DESCRIPTION
				"Description."
			::= { dhcpServerPoolEntry 5 }

		
		-- 1.3.6.1.4.1.34592.1.3.100.5.10
		dhcpServerStaticPoolTable OBJECT-TYPE
			SYNTAX SEQUENCE OF DhcpServerStaticPoolEntry
			MAX-ACCESS not-accessible
			STATUS current
			DESCRIPTION
				"Description.
				DHCP Server 静态地址池查看表"
			::= { dhcpManagementObjects 10 }

		
		-- 1.3.6.1.4.1.34592.1.3.100.5.10.1
		dhcpServerStaticPoolEntry OBJECT-TYPE
			SYNTAX DhcpServerStaticPoolEntry
			MAX-ACCESS not-accessible
			STATUS current
			DESCRIPTION
				"Description.
				DHCP Server 静态地址池查看表目"
			INDEX { dhcpServerStaticPoolDeviceIndex }
			::= { dhcpServerStaticPoolTable 1 }

		
		DhcpServerStaticPoolEntry ::=
			SEQUENCE { 
				dhcpServerStaticPoolDeviceIndex
					NscrtvPonExtDeviceIndex,
				dhcpServerStaticPoolIpAddr
					IpAddress,
				dhcpServerStaticPoolMac
					MacAddress,
				dhcpServerStaticPoolRowStatus
					RowStatus
			 }

		-- 1.3.6.1.4.1.34592.1.3.100.5.10.1.1
		dhcpServerStaticPoolDeviceIndex OBJECT-TYPE
			SYNTAX NscrtvPonExtDeviceIndex
			MAX-ACCESS not-accessible
			STATUS current
			DESCRIPTION
				"Description."
			::= { dhcpServerStaticPoolEntry 1 }

		
		-- 1.3.6.1.4.1.34592.1.3.100.5.10.1.2
		dhcpServerStaticPoolIpAddr OBJECT-TYPE
			SYNTAX IpAddress
			MAX-ACCESS read-create
			STATUS current
			DESCRIPTION
				"Description."
			::= { dhcpServerStaticPoolEntry 2 }

		
		-- 1.3.6.1.4.1.34592.1.3.100.5.10.1.3
		dhcpServerStaticPoolMac OBJECT-TYPE
			SYNTAX MacAddress
			MAX-ACCESS read-create
			STATUS current
			DESCRIPTION
				"Description."
			::= { dhcpServerStaticPoolEntry 3 }

		
		-- 1.3.6.1.4.1.34592.1.3.100.5.10.1.4
		dhcpServerStaticPoolRowStatus OBJECT-TYPE
			SYNTAX RowStatus
			MAX-ACCESS read-create
			STATUS current
			DESCRIPTION
				"Description."
			::= { dhcpServerStaticPoolEntry 4 }

		
		-- 1.3.6.1.4.1.34592.1.3.100.5.11
		dhcpClientTable OBJECT-TYPE
			SYNTAX SEQUENCE OF DhcpClientEntry
			MAX-ACCESS not-accessible
			STATUS current
			DESCRIPTION
				"Description."
			::= { dhcpManagementObjects 11 }

		
		-- 1.3.6.1.4.1.34592.1.3.100.5.11.1
		dhcpClientEntry OBJECT-TYPE
			SYNTAX DhcpClientEntry
			MAX-ACCESS not-accessible
			STATUS current
			DESCRIPTION
				"Description."
			INDEX { dhcpClientVlanId }
			::= { dhcpClientTable 1 }

		
		DhcpClientEntry ::=
			SEQUENCE { 
				dhcpClientVlanId
					Unsigned32,
				dhcpClientFSM
					OCTET STRING,
				dhcpClientIpAddr
					IpAddress,
				dhcpClientSubNetMask
					Unsigned32,
				dhcpClientLeasedUntilTime
					Unsigned32,
				dhcpClientAdmin
					RowStatus,
				dhcpClientOption60
					OCTET STRING,
				dhcpClientOptionRelease
					RowStatus,
				dhcpClientOptionRenew
					RowStatus
			 }

		-- 1.3.6.1.4.1.34592.1.3.100.5.11.1.1
		dhcpClientVlanId OBJECT-TYPE
			SYNTAX Unsigned32
			MAX-ACCESS not-accessible
			STATUS current
			DESCRIPTION
				"Description."
			::= { dhcpClientEntry 1 }

		
		-- 1.3.6.1.4.1.34592.1.3.100.5.11.1.2
		dhcpClientFSM OBJECT-TYPE
			SYNTAX OCTET STRING
			MAX-ACCESS read-only
			STATUS current
			DESCRIPTION
				"Description."
			::= { dhcpClientEntry 2 }

		
		-- 1.3.6.1.4.1.34592.1.3.100.5.11.1.3
		dhcpClientIpAddr OBJECT-TYPE
			SYNTAX IpAddress
			MAX-ACCESS read-only
			STATUS current
			DESCRIPTION
				"Description."
			::= { dhcpClientEntry 3 }

		
		-- 1.3.6.1.4.1.34592.1.3.100.5.11.1.4
		dhcpClientSubNetMask OBJECT-TYPE
			SYNTAX Unsigned32
			MAX-ACCESS read-only
			STATUS current
			DESCRIPTION
				"Description."
			::= { dhcpClientEntry 4 }

		
		-- 1.3.6.1.4.1.34592.1.3.100.5.11.1.5
		dhcpClientLeasedUntilTime OBJECT-TYPE
			SYNTAX Unsigned32
			MAX-ACCESS read-only
			STATUS current
			DESCRIPTION
				"Description."
			::= { dhcpClientEntry 5 }

		
		-- 1.3.6.1.4.1.34592.1.3.100.5.11.1.6
		dhcpClientAdmin OBJECT-TYPE
			SYNTAX RowStatus
				{
				disable(0),
				enable(1)
				}
			MAX-ACCESS read-write
			STATUS current
			DESCRIPTION
				"Description."
			::= { dhcpClientEntry 6 }

		
		-- 1.3.6.1.4.1.34592.1.3.100.5.11.1.7
		dhcpClientOption60 OBJECT-TYPE
			SYNTAX OCTET STRING (SIZE (1..32))
			MAX-ACCESS read-write
			STATUS current
			DESCRIPTION
				"Description."
			::= { dhcpClientEntry 7 }

		
		-- 1.3.6.1.4.1.34592.1.3.100.5.11.1.8
		dhcpClientOptionRelease OBJECT-TYPE
			SYNTAX RowStatus
				{
				disable(0),
				enable(1)
				}
			MAX-ACCESS read-write
			STATUS current
			DESCRIPTION
				"Description."
			::= { dhcpClientEntry 8 }

		
		-- 1.3.6.1.4.1.34592.1.3.100.5.11.1.9
		dhcpClientOptionRenew OBJECT-TYPE
			SYNTAX RowStatus
				{
				disable(0),
				enable(1)
				}
			MAX-ACCESS read-write
			STATUS current
			DESCRIPTION
				"Description."
			::= { dhcpClientEntry 9 }

		
		-- 1.3.6.1.4.1.34592.1.3.100.6
		arpManagementObjects OBJECT IDENTIFIER ::= { nscrtvPonTreeExt 6 }

		
		-- 1.3.6.1.4.1.34592.1.3.100.6.1
		arpConfigTable OBJECT-TYPE
			SYNTAX SEQUENCE OF ArpConfigEntry
			MAX-ACCESS not-accessible
			STATUS current
			DESCRIPTION
				"Description."
			::= { arpManagementObjects 1 }

		
		-- 1.3.6.1.4.1.34592.1.3.100.6.1.1
		arpConfigEntry OBJECT-TYPE
			SYNTAX ArpConfigEntry
			MAX-ACCESS not-accessible
			STATUS current
			DESCRIPTION
				"Description."
			INDEX { arpConfigDeviceIndex }
			::= { arpConfigTable 1 }

		
		ArpConfigEntry ::=
			SEQUENCE { 
				arpConfigDeviceIndex
					NscrtvPonExtDeviceIndex,
				arpConfigMaxLearnNum
					Unsigned32,
				arpConfigCurrentLearnNum
					Unsigned32,
				arpConfigQuickUpdateEnable
					TruthValue,
				arpConfigReplyFastEnable
					TruthValue,
				arpConfigDetectEnable
					TruthValue,
				arpConfigAgeTime
					Unsigned32,
				arpConfigGratuitousArpSendTime
					Integer32,
				arpConfigGratuitousArpLearnEnable
					TruthValue,
				arpConfigArpClear
					INTEGER,
				arpConfigGratuitousArpSendEnable
					TruthValue
			 }

		-- 1.3.6.1.4.1.34592.1.3.100.6.1.1.1
		arpConfigDeviceIndex OBJECT-TYPE
			SYNTAX NscrtvPonExtDeviceIndex
			MAX-ACCESS not-accessible
			STATUS current
			DESCRIPTION
				"Description."
			::= { arpConfigEntry 1 }

		
		-- 1.3.6.1.4.1.34592.1.3.100.6.1.1.2
		arpConfigMaxLearnNum OBJECT-TYPE
			SYNTAX Unsigned32
			MAX-ACCESS read-only
			STATUS current
			DESCRIPTION
				"Description."
			::= { arpConfigEntry 2 }

		
		-- 1.3.6.1.4.1.34592.1.3.100.6.1.1.3
		arpConfigCurrentLearnNum OBJECT-TYPE
			SYNTAX Unsigned32
			MAX-ACCESS read-only
			STATUS current
			DESCRIPTION
				"Description."
			::= { arpConfigEntry 3 }

		
		-- 1.3.6.1.4.1.34592.1.3.100.6.1.1.4
		arpConfigQuickUpdateEnable OBJECT-TYPE
			SYNTAX TruthValue
			MAX-ACCESS read-write
			STATUS current
			DESCRIPTION
				"Description."
			::= { arpConfigEntry 4 }

		
		-- 1.3.6.1.4.1.34592.1.3.100.6.1.1.5
		arpConfigReplyFastEnable OBJECT-TYPE
			SYNTAX TruthValue
			MAX-ACCESS read-write
			STATUS current
			DESCRIPTION
				"Description."
			::= { arpConfigEntry 5 }

		
		-- 1.3.6.1.4.1.34592.1.3.100.6.1.1.6
		arpConfigDetectEnable OBJECT-TYPE
			SYNTAX TruthValue
			MAX-ACCESS read-write
			STATUS current
			DESCRIPTION
				"Description."
			::= { arpConfigEntry 6 }

		
		-- 1.3.6.1.4.1.34592.1.3.100.6.1.1.8
		arpConfigAgeTime OBJECT-TYPE
			SYNTAX Unsigned32 (60..300)
			MAX-ACCESS read-write
			STATUS current
			DESCRIPTION
				"Description."
			::= { arpConfigEntry 8 }

		
		-- 1.3.6.1.4.1.34592.1.3.100.6.1.1.9
		arpConfigGratuitousArpSendTime OBJECT-TYPE
			SYNTAX Integer32 (1..60)
			MAX-ACCESS read-write
			STATUS current
			DESCRIPTION
				"Description."
			::= { arpConfigEntry 9 }

		
		-- 1.3.6.1.4.1.34592.1.3.100.6.1.1.10
		arpConfigGratuitousArpLearnEnable OBJECT-TYPE
			SYNTAX TruthValue
			MAX-ACCESS read-write
			STATUS current
			DESCRIPTION
				"Description."
			::= { arpConfigEntry 10 }

		
		-- 1.3.6.1.4.1.34592.1.3.100.6.1.1.11
		arpConfigArpClear OBJECT-TYPE
			SYNTAX INTEGER
				{
				allDynamic(1),
				allStatic(2),
				none(3)
				}
			MAX-ACCESS read-write
			STATUS current
			DESCRIPTION
				"Description."
			::= { arpConfigEntry 11 }

		
		-- 1.3.6.1.4.1.34592.1.3.100.6.1.1.12
		arpConfigGratuitousArpSendEnable OBJECT-TYPE
			SYNTAX TruthValue
			MAX-ACCESS read-write
			STATUS current
			DESCRIPTION
				"Description."
			::= { arpConfigEntry 12 }

		
		-- 1.3.6.1.4.1.34592.1.3.100.6.2
		arpTable OBJECT-TYPE
			SYNTAX SEQUENCE OF ArpEntry
			MAX-ACCESS not-accessible
			STATUS current
			DESCRIPTION
				"Description."
			::= { arpManagementObjects 2 }

		
		-- 1.3.6.1.4.1.34592.1.3.100.6.2.1
		arpEntry OBJECT-TYPE
			SYNTAX ArpEntry
			MAX-ACCESS not-accessible
			STATUS current
			DESCRIPTION
				"Description."
			INDEX { arpTableIpAddressIndex, arpTableVlanIndex }
			::= { arpTable 1 }

		
		ArpEntry ::=
			SEQUENCE { 
				arpTableIpAddressIndex
					IpAddress,
				arpTableVlanIndex
					Unsigned32,
				arpTableMacAddress
					MacAddress,
				arpTablePortId
					NscrtvPonExtDeviceIndex,
				arpTableType
					INTEGER,
				arpTableRowStatus
					RowStatus,
				arpTableAgingTime
					Integer32
			 }

		-- 1.3.6.1.4.1.34592.1.3.100.6.2.1.1
		arpTableIpAddressIndex OBJECT-TYPE
			SYNTAX IpAddress
			MAX-ACCESS not-accessible
			STATUS current
			DESCRIPTION
				"Description."
			::= { arpEntry 1 }

		
		-- 1.3.6.1.4.1.34592.1.3.100.6.2.1.2
		arpTableVlanIndex OBJECT-TYPE
			SYNTAX Unsigned32
			MAX-ACCESS not-accessible
			STATUS current
			DESCRIPTION
				"Description."
			::= { arpEntry 2 }

		
		-- 1.3.6.1.4.1.34592.1.3.100.6.2.1.3
		arpTableMacAddress OBJECT-TYPE
			SYNTAX MacAddress
			MAX-ACCESS read-create
			STATUS current
			DESCRIPTION
				"Description."
			::= { arpEntry 3 }

		
		-- 1.3.6.1.4.1.34592.1.3.100.6.2.1.4
		arpTablePortId OBJECT-TYPE
			SYNTAX NscrtvPonExtDeviceIndex
			MAX-ACCESS read-create
			STATUS current
			DESCRIPTION
				"Description."
			::= { arpEntry 4 }

		
		-- 1.3.6.1.4.1.34592.1.3.100.6.2.1.5
		arpTableType OBJECT-TYPE
			SYNTAX INTEGER
				{
				dynamic(1),
				static(2)
				}
			MAX-ACCESS read-create
			STATUS current
			DESCRIPTION
				"Description."
			::= { arpEntry 5 }

		
		-- 1.3.6.1.4.1.34592.1.3.100.6.2.1.6
		arpTableRowStatus OBJECT-TYPE
			SYNTAX RowStatus
			MAX-ACCESS read-create
			STATUS current
			DESCRIPTION
				"Description."
			::= { arpEntry 6 }

		
		-- 1.3.6.1.4.1.34592.1.3.100.6.2.1.7
		arpTableAgingTime OBJECT-TYPE
			SYNTAX Integer32
			MAX-ACCESS read-only
			STATUS current
			DESCRIPTION
				"Description."
			::= { arpEntry 7 }

		
		-- 1.3.6.1.4.1.34592.1.3.100.6.3
		arpVlanIfConfigTable OBJECT-TYPE
			SYNTAX SEQUENCE OF ArpVlanIfConfigEntry
			MAX-ACCESS not-accessible
			STATUS current
			DESCRIPTION
				"Description."
			::= { arpManagementObjects 3 }

		
		-- 1.3.6.1.4.1.34592.1.3.100.6.3.1
		arpVlanIfConfigEntry OBJECT-TYPE
			SYNTAX ArpVlanIfConfigEntry
			MAX-ACCESS not-accessible
			STATUS current
			DESCRIPTION
				"Description."
			INDEX { arpVlanIfConfigDeviceIndex, arpVlanIfConfigVlanIfIndex }
			::= { arpVlanIfConfigTable 1 }

		
		ArpVlanIfConfigEntry ::=
			SEQUENCE { 
				arpVlanIfConfigDeviceIndex
					NscrtvPonExtDeviceIndex,
				arpVlanIfConfigVlanIfIndex
					Unsigned32,
				arpVlanIfConfigArpClear
					INTEGER,
				arpVlanifConfigProxyEnable
					TruthValue,
				arpVlanifConfigInnerVlanArpProxyEnable
					TruthValue,
				arpVlanifConfigGratuitousArpSendEnable
					TruthValue
			 }

		-- 1.3.6.1.4.1.34592.1.3.100.6.3.1.1
		arpVlanIfConfigDeviceIndex OBJECT-TYPE
			SYNTAX NscrtvPonExtDeviceIndex
			MAX-ACCESS not-accessible
			STATUS current
			DESCRIPTION
				"Description."
			::= { arpVlanIfConfigEntry 1 }

		
		-- 1.3.6.1.4.1.34592.1.3.100.6.3.1.2
		arpVlanIfConfigVlanIfIndex OBJECT-TYPE
			SYNTAX Unsigned32
			MAX-ACCESS not-accessible
			STATUS current
			DESCRIPTION
				"Description."
			::= { arpVlanIfConfigEntry 2 }

		
		-- 1.3.6.1.4.1.34592.1.3.100.6.3.1.3
		arpVlanIfConfigArpClear OBJECT-TYPE
			SYNTAX INTEGER
				{
				dynamic(1),
				static(2),
				none(3)
				}
			MAX-ACCESS read-write
			STATUS current
			DESCRIPTION
				"Description."
			::= { arpVlanIfConfigEntry 3 }

		
		-- 1.3.6.1.4.1.34592.1.3.100.6.3.1.4
		arpVlanifConfigProxyEnable OBJECT-TYPE
			SYNTAX TruthValue
			MAX-ACCESS read-write
			STATUS current
			DESCRIPTION
				"Description."
			::= { arpVlanIfConfigEntry 4 }

		
		-- 1.3.6.1.4.1.34592.1.3.100.6.3.1.5
		arpVlanifConfigInnerVlanArpProxyEnable OBJECT-TYPE
			SYNTAX TruthValue
			MAX-ACCESS read-write
			STATUS current
			DESCRIPTION
				"Description."
			::= { arpVlanIfConfigEntry 5 }

		
		-- 1.3.6.1.4.1.34592.1.3.100.6.3.1.6
		arpVlanifConfigGratuitousArpSendEnable OBJECT-TYPE
			SYNTAX TruthValue
			MAX-ACCESS read-write
			STATUS current
			DESCRIPTION
				"Description."
			::= { arpVlanIfConfigEntry 6 }

		
		-- 1.3.6.1.4.1.34592.1.3.100.6.4
		arpMgmtTable OBJECT-TYPE
			SYNTAX SEQUENCE OF ArpMgmtEntry
			MAX-ACCESS not-accessible
			STATUS current
			DESCRIPTION
				"Description."
			::= { arpManagementObjects 4 }

		
		-- 1.3.6.1.4.1.34592.1.3.100.6.4.1
		arpMgmtEntry OBJECT-TYPE
			SYNTAX ArpMgmtEntry
			MAX-ACCESS not-accessible
			STATUS current
			DESCRIPTION
				"Description."
			INDEX { arpMgmtTableIpAddressIndex }
			::= { arpMgmtTable 1 }

		
		ArpMgmtEntry ::=
			SEQUENCE { 
				arpMgmtTableIpAddressIndex
					IpAddress,
				arpMgmtMacAddress
					MacAddress,
				arpMgmtType
					INTEGER,
				arpMgmtFlag
					INTEGER
			 }

		-- 1.3.6.1.4.1.34592.1.3.100.6.4.1.1
		arpMgmtTableIpAddressIndex OBJECT-TYPE
			SYNTAX IpAddress
			MAX-ACCESS not-accessible
			STATUS current
			DESCRIPTION
				"Description."
			::= { arpMgmtEntry 1 }

		
		-- 1.3.6.1.4.1.34592.1.3.100.6.4.1.2
		arpMgmtMacAddress OBJECT-TYPE
			SYNTAX MacAddress
			MAX-ACCESS read-only
			STATUS current
			DESCRIPTION
				"Description."
			::= { arpMgmtEntry 2 }

		
		-- 1.3.6.1.4.1.34592.1.3.100.6.4.1.3
		arpMgmtType OBJECT-TYPE
			SYNTAX INTEGER
				{
				Netrom(0),
				Ether(1),
				EEther(2),
				AX25(3),
				PROnet(4),
				Chaosnet(5),
				IEEE802(6),
				ARCnet(7),
				APPLEtalk(8),
				DLCI(15),
				ATM(19),
				Metricom(23),
				IEEE1394(24),
				EUI64(28),
				InfiniBand(32)
				}
			MAX-ACCESS read-only
			STATUS current
			DESCRIPTION
				"Description."
			::= { arpMgmtEntry 3 }

		
		-- 1.3.6.1.4.1.34592.1.3.100.6.4.1.4
		arpMgmtFlag OBJECT-TYPE
			SYNTAX INTEGER
				{
				COM(2),
				PERM(4),
				PUBL(8),
				USETRAILERS(16),
				NETMASK(32),
				DONTPUB(64)
				}
			MAX-ACCESS read-only
			STATUS current
			DESCRIPTION
				"Description."
			::= { arpMgmtEntry 4 }

		
		-- 1.3.6.1.4.1.34592.1.3.100.6.5
		arpStaticTable OBJECT-TYPE
			SYNTAX SEQUENCE OF ArpStaticEntry
			MAX-ACCESS not-accessible
			STATUS current
			DESCRIPTION
				"Description."
			::= { arpManagementObjects 5 }

		
		-- 1.3.6.1.4.1.34592.1.3.100.6.5.1
		arpStaticEntry OBJECT-TYPE
			SYNTAX ArpStaticEntry
			MAX-ACCESS not-accessible
			STATUS current
			DESCRIPTION
				"Description."
			INDEX { arpStaticIpAddressIndex, arpStaticVlanIndex }
			::= { arpStaticTable 1 }

		
		ArpStaticEntry ::=
			SEQUENCE { 
				arpStaticIpAddressIndex
					IpAddress,
				arpStaticVlanIndex
					Unsigned32,
				arpStaticMacAddress
					MacAddress,
				arpStaticPortId
					NscrtvPonExtDeviceIndex,
				arpStaticOnuId
					Unsigned32,
				arpStaticGemId
					Unsigned32,
				arpStaticType
					INTEGER,
				arpStaticRowStatus
					RowStatus
			 }

		-- 1.3.6.1.4.1.34592.1.3.100.6.5.1.1
		arpStaticIpAddressIndex OBJECT-TYPE
			SYNTAX IpAddress
			MAX-ACCESS not-accessible
			STATUS current
			DESCRIPTION
				"Description."
			::= { arpStaticEntry 1 }

		
		-- 1.3.6.1.4.1.34592.1.3.100.6.5.1.2
		arpStaticVlanIndex OBJECT-TYPE
			SYNTAX Unsigned32
			MAX-ACCESS not-accessible
			STATUS current
			DESCRIPTION
				"Description."
			::= { arpStaticEntry 2 }

		
		-- 1.3.6.1.4.1.34592.1.3.100.6.5.1.3
		arpStaticMacAddress OBJECT-TYPE
			SYNTAX MacAddress
			MAX-ACCESS read-create
			STATUS current
			DESCRIPTION
				"Description."
			::= { arpStaticEntry 3 }

		
		-- 1.3.6.1.4.1.34592.1.3.100.6.5.1.4
		arpStaticPortId OBJECT-TYPE
			SYNTAX NscrtvPonExtDeviceIndex
			MAX-ACCESS read-create
			STATUS current
			DESCRIPTION
				"Description."
			::= { arpStaticEntry 4 }

		
		-- 1.3.6.1.4.1.34592.1.3.100.6.5.1.5
		arpStaticOnuId OBJECT-TYPE
			SYNTAX Unsigned32
			MAX-ACCESS read-create
			STATUS current
			DESCRIPTION
				"Description."
			::= { arpStaticEntry 5 }

		
		-- 1.3.6.1.4.1.34592.1.3.100.6.5.1.6
		arpStaticGemId OBJECT-TYPE
			SYNTAX Unsigned32
			MAX-ACCESS read-create
			STATUS current
			DESCRIPTION
				"Description."
			::= { arpStaticEntry 6 }

		
		-- 1.3.6.1.4.1.34592.1.3.100.6.5.1.8
		arpStaticType OBJECT-TYPE
			SYNTAX INTEGER
				{
				dynamic(1),
				static(2)
				}
			MAX-ACCESS read-create
			STATUS current
			DESCRIPTION
				"Description."
			::= { arpStaticEntry 8 }

		
		-- 1.3.6.1.4.1.34592.1.3.100.6.5.1.9
		arpStaticRowStatus OBJECT-TYPE
			SYNTAX RowStatus
			MAX-ACCESS read-create
			STATUS current
			DESCRIPTION
				"Description."
			::= { arpStaticEntry 9 }

		
		-- 1.3.6.1.4.1.34592.1.3.100.6.6
		arpCollectTable OBJECT-TYPE
			SYNTAX SEQUENCE OF ArpCollectEntry
			MAX-ACCESS not-accessible
			STATUS current
			DESCRIPTION
				"Description."
			::= { arpManagementObjects 6 }

		
		-- 1.3.6.1.4.1.34592.1.3.100.6.6.1
		arpCollectEntry OBJECT-TYPE
			SYNTAX ArpCollectEntry
			MAX-ACCESS not-accessible
			STATUS current
			DESCRIPTION
				"Description."
			INDEX { arpCollectIndex }
			::= { arpCollectTable 1 }

		
		ArpCollectEntry ::=
			SEQUENCE { 
				arpCollectIndex
					Integer32,
				arpCollectInfo
					OCTET STRING
			 }

		-- 1.3.6.1.4.1.34592.1.3.100.6.6.1.1
		arpCollectIndex OBJECT-TYPE
			SYNTAX Integer32
			MAX-ACCESS not-accessible
			STATUS current
			DESCRIPTION
				"Description."
			::= { arpCollectEntry 1 }

		
		-- 1.3.6.1.4.1.34592.1.3.100.6.6.1.2
		arpCollectInfo OBJECT-TYPE
			SYNTAX OCTET STRING
			MAX-ACCESS read-only
			STATUS current
			DESCRIPTION
				"Description."
			::= { arpCollectEntry 2 }

		
		-- 1.3.6.1.4.1.34592.1.3.100.8
		ppoeManagementObjects OBJECT IDENTIFIER ::= { nscrtvPonTreeExt 8 }

		
		-- 1.3.6.1.4.1.34592.1.3.100.8.1
		ppoePlusConfigTable OBJECT-TYPE
			SYNTAX SEQUENCE OF PpoePlusConfigEntry
			MAX-ACCESS not-accessible
			STATUS current
			DESCRIPTION
				"Description."
			::= { ppoeManagementObjects 1 }

		
		-- 1.3.6.1.4.1.34592.1.3.100.8.1.1
		ppoePlusConfigEntry OBJECT-TYPE
			SYNTAX PpoePlusConfigEntry
			MAX-ACCESS not-accessible
			STATUS current
			DESCRIPTION
				"Description."
			INDEX { ppoePlusConfigDeviceIndex }
			::= { ppoePlusConfigTable 1 }

		
		PpoePlusConfigEntry ::=
			SEQUENCE { 
				ppoePlusConfigDeviceIndex
					NscrtvPonExtDeviceIndex,
				ppoePlusConfigEnable
					TruthValue,
				ppoePlusConfigPolicy
					INTEGER,
				ppoePlusConfigFormat
					OCTET STRING
			 }

		-- 1.3.6.1.4.1.34592.1.3.100.8.1.1.1
		ppoePlusConfigDeviceIndex OBJECT-TYPE
			SYNTAX NscrtvPonExtDeviceIndex
			MAX-ACCESS not-accessible
			STATUS current
			DESCRIPTION
				"Description."
			::= { ppoePlusConfigEntry 1 }

		
		-- 1.3.6.1.4.1.34592.1.3.100.8.1.1.2
		ppoePlusConfigEnable OBJECT-TYPE
			SYNTAX TruthValue
			MAX-ACCESS read-write
			STATUS current
			DESCRIPTION
				"Description."
			::= { ppoePlusConfigEntry 2 }

		
		-- 1.3.6.1.4.1.34592.1.3.100.8.1.1.3
		ppoePlusConfigPolicy OBJECT-TYPE
			SYNTAX INTEGER
				{
				keep(1),
				drop(2),
				replace(3)
				}
			MAX-ACCESS read-write
			STATUS current
			DESCRIPTION
				"Description."
			::= { ppoePlusConfigEntry 3 }

		
		-- 1.3.6.1.4.1.34592.1.3.100.8.1.1.4
		ppoePlusConfigFormat OBJECT-TYPE
			SYNTAX OCTET STRING (SIZE (1..32))
			MAX-ACCESS read-write
			STATUS current
			DESCRIPTION
				"此处显示的是Format的名称，设置时填写的也是Format的名称，
				可通过下表pppoeAgentOption82FormatTable查看设备中已有的Format信息。"
			::= { ppoePlusConfigEntry 4 }

		
		-- 1.3.6.1.4.1.34592.1.3.100.8.2
		pppoeAgentOption82FormatTable OBJECT-TYPE
			SYNTAX SEQUENCE OF PppoeAgentOption82FormatEntry
			MAX-ACCESS not-accessible
			STATUS current
			DESCRIPTION
				"pppoe Agent option82字段格式表"
			::= { ppoeManagementObjects 2 }

		
		-- 1.3.6.1.4.1.34592.1.3.100.8.2.1
		pppoeAgentOption82FormatEntry OBJECT-TYPE
			SYNTAX PppoeAgentOption82FormatEntry
			MAX-ACCESS not-accessible
			STATUS current
			DESCRIPTION
				"pppoe Agent option82字段格式表目"
			INDEX { pppoeAgentOption82FormatDeviceIndex, pppoeAgentOption82FormatIndex }
			::= { pppoeAgentOption82FormatTable 1 }

		
		PppoeAgentOption82FormatEntry ::=
			SEQUENCE { 
				pppoeAgentOption82FormatDeviceIndex
					NscrtvPonExtDeviceIndex,
				pppoeAgentOption82FormatIndex
					Unsigned32,
				pppoeAgentOption82FormatName
					OCTET STRING,
				pppoeAgentOption82FormatCodeType
					INTEGER,
				pppoeAgentOption82FormatCircuitId
					OCTET STRING,
				pppoeAgentOption82FormatRemoteId
					OCTET STRING,
				pppoeAgentOption82FormatRowStatus
					RowStatus
			 }

		-- 1.3.6.1.4.1.34592.1.3.100.8.2.1.1
		pppoeAgentOption82FormatDeviceIndex OBJECT-TYPE
			SYNTAX NscrtvPonExtDeviceIndex
			MAX-ACCESS not-accessible
			STATUS current
			DESCRIPTION
				"OLT设备索引号"
			::= { pppoeAgentOption82FormatEntry 1 }

		
		-- 1.3.6.1.4.1.34592.1.3.100.8.2.1.2
		pppoeAgentOption82FormatIndex OBJECT-TYPE
			SYNTAX Unsigned32 (1..8)
			MAX-ACCESS not-accessible
			STATUS current
			DESCRIPTION
				"pppoe Agent option82字段格式项索引"
			::= { pppoeAgentOption82FormatEntry 2 }

		
		-- 1.3.6.1.4.1.34592.1.3.100.8.2.1.3
		pppoeAgentOption82FormatName OBJECT-TYPE
			SYNTAX OCTET STRING (SIZE (1..32))
			MAX-ACCESS read-create
			STATUS current
			DESCRIPTION
				"pppoe Agent option82字段格式项名称"
			::= { pppoeAgentOption82FormatEntry 3 }

		
		-- 1.3.6.1.4.1.34592.1.3.100.8.2.1.4
		pppoeAgentOption82FormatCodeType OBJECT-TYPE
			SYNTAX INTEGER
				{
				ascii(1),
				hex(2)
				}
			MAX-ACCESS read-create
			STATUS current
			DESCRIPTION
				"pppoe Agent option82字段格式项类型"
			::= { pppoeAgentOption82FormatEntry 4 }

		
		-- 1.3.6.1.4.1.34592.1.3.100.8.2.1.5
		pppoeAgentOption82FormatCircuitId OBJECT-TYPE
			SYNTAX OCTET STRING (SIZE (1..128))
			MAX-ACCESS read-write
			STATUS current
			DESCRIPTION
				"pppoe Agent option82字段格式项Circuit Id"
			::= { pppoeAgentOption82FormatEntry 5 }

		
		-- 1.3.6.1.4.1.34592.1.3.100.8.2.1.6
		pppoeAgentOption82FormatRemoteId OBJECT-TYPE
			SYNTAX OCTET STRING (SIZE (1..128))
			MAX-ACCESS read-write
			STATUS current
			DESCRIPTION
				"pppoe Agent option82字段格式项Remote Id"
			::= { pppoeAgentOption82FormatEntry 6 }

		
		-- 1.3.6.1.4.1.34592.1.3.100.8.2.1.7
		pppoeAgentOption82FormatRowStatus OBJECT-TYPE
			SYNTAX RowStatus
			MAX-ACCESS read-create
			STATUS current
			DESCRIPTION
				"使用该节点创建表项时，必选参数pppoeAgentOption82FormatName、pppoeAgentOption82FormatType；
				pppoeAgentOption82FormatCircuitId和pppoeAgentOption82FormatRemoteId二选一或者同时选择。"
			::= { pppoeAgentOption82FormatEntry 7 }

		
		-- 1.3.6.1.4.1.34592.1.3.100.10
		loopBackDetectionManagementObjects OBJECT IDENTIFIER ::= { nscrtvPonTreeExt 10 }

		
		-- 1.3.6.1.4.1.34592.1.3.100.10.1
		loopBackDetectionGlobalSetTable OBJECT-TYPE
			SYNTAX SEQUENCE OF LoopBackDetectionGlobalSetEntry
			MAX-ACCESS not-accessible
			STATUS current
			DESCRIPTION
				"Description."
			::= { loopBackDetectionManagementObjects 1 }

		
		-- 1.3.6.1.4.1.34592.1.3.100.10.1.1
		loopBackDetectionGlobalSetEntry OBJECT-TYPE
			SYNTAX LoopBackDetectionGlobalSetEntry
			MAX-ACCESS not-accessible
			STATUS current
			DESCRIPTION
				"Description."
			INDEX { loopBackDetectionGloabDeviceIndex }
			::= { loopBackDetectionGlobalSetTable 1 }

		
		LoopBackDetectionGlobalSetEntry ::=
			SEQUENCE { 
				loopBackDetectionGloabDeviceIndex
					NscrtvPonExtDeviceIndex,
				loopBackDetectionGlobalEnable
					TruthValue,
				loopBackDetectionGlobalInterval
					Unsigned32
			 }

		-- 1.3.6.1.4.1.34592.1.3.100.10.1.1.1
		loopBackDetectionGloabDeviceIndex OBJECT-TYPE
			SYNTAX NscrtvPonExtDeviceIndex
			MAX-ACCESS not-accessible
			STATUS current
			DESCRIPTION
				"Description."
			::= { loopBackDetectionGlobalSetEntry 1 }

		
		-- 1.3.6.1.4.1.34592.1.3.100.10.1.1.2
		loopBackDetectionGlobalEnable OBJECT-TYPE
			SYNTAX TruthValue
			MAX-ACCESS read-write
			STATUS current
			DESCRIPTION
				"Description."
			::= { loopBackDetectionGlobalSetEntry 2 }

		
		-- 1.3.6.1.4.1.34592.1.3.100.10.1.1.3
		loopBackDetectionGlobalInterval OBJECT-TYPE
			SYNTAX Unsigned32 (5..300)
			MAX-ACCESS read-write
			STATUS current
			DESCRIPTION
				"Description."
			::= { loopBackDetectionGlobalSetEntry 3 }

		
		-- 1.3.6.1.4.1.34592.1.3.100.10.2
		loopBackDetectionPortConfigTable OBJECT-TYPE
			SYNTAX SEQUENCE OF LoopBackDetectionPortConfigEntry
			MAX-ACCESS not-accessible
			STATUS current
			DESCRIPTION
				"Description."
			::= { loopBackDetectionManagementObjects 2 }

		
		-- 1.3.6.1.4.1.34592.1.3.100.10.2.1
		loopBackDetectionPortConfigEntry OBJECT-TYPE
			SYNTAX LoopBackDetectionPortConfigEntry
			MAX-ACCESS not-accessible
			STATUS current
			DESCRIPTION
				"Description."
			INDEX { loopBackDetectionPortConfigDeviceIndex, loopBackDetectionPortConfigCardIndex, loopBackDetectionPortConfigPortIndex }
			::= { loopBackDetectionPortConfigTable 1 }

		
		LoopBackDetectionPortConfigEntry ::=
			SEQUENCE { 
				loopBackDetectionPortConfigDeviceIndex
					NscrtvPonExtDeviceIndex,
				loopBackDetectionPortConfigCardIndex
					NscrtvPonExtCardIndex,
				loopBackDetectionPortConfigPortIndex
					NscrtvPonPortIndex,
				loopBackDetectionPortConfigEnable
					TruthValue,
				loopBackDetectionPortConfigPerVlanEnable
					TruthValue,
				loopBackDetectionPortConfigControlEnable
					INTEGER,
				loopBackDetectionPortStatus
					INTEGER,
				loopBackDetectionPortConfigAutoRecoverEnable
					INTEGER,
				loopBackDetectionPortConfigAutoRecoverTime
					INTEGER
			 }

		-- 1.3.6.1.4.1.34592.1.3.100.10.2.1.1
		loopBackDetectionPortConfigDeviceIndex OBJECT-TYPE
			SYNTAX NscrtvPonExtDeviceIndex
			MAX-ACCESS not-accessible
			STATUS current
			DESCRIPTION
				"Description."
			::= { loopBackDetectionPortConfigEntry 1 }

		
		-- 1.3.6.1.4.1.34592.1.3.100.10.2.1.2
		loopBackDetectionPortConfigCardIndex OBJECT-TYPE
			SYNTAX NscrtvPonExtCardIndex
			MAX-ACCESS not-accessible
			STATUS current
			DESCRIPTION
				"Description."
			::= { loopBackDetectionPortConfigEntry 2 }

		
		-- 1.3.6.1.4.1.34592.1.3.100.10.2.1.3
		loopBackDetectionPortConfigPortIndex OBJECT-TYPE
			SYNTAX NscrtvPonPortIndex
			MAX-ACCESS not-accessible
			STATUS current
			DESCRIPTION
				"Description."
			::= { loopBackDetectionPortConfigEntry 3 }

		
		-- 1.3.6.1.4.1.34592.1.3.100.10.2.1.4
		loopBackDetectionPortConfigEnable OBJECT-TYPE
			SYNTAX TruthValue
			MAX-ACCESS read-write
			STATUS current
			DESCRIPTION
				"Description."
			::= { loopBackDetectionPortConfigEntry 4 }

		
		-- 1.3.6.1.4.1.34592.1.3.100.10.2.1.5
		loopBackDetectionPortConfigPerVlanEnable OBJECT-TYPE
			SYNTAX TruthValue
			MAX-ACCESS read-write
			STATUS current
			DESCRIPTION
				"Description."
			::= { loopBackDetectionPortConfigEntry 5 }

		
		-- 1.3.6.1.4.1.34592.1.3.100.10.2.1.6
		loopBackDetectionPortConfigControlEnable OBJECT-TYPE
			SYNTAX INTEGER
				{
				disable(0),
				block(1),
				no-learning(2),
				shutdown(3)
				}
			MAX-ACCESS read-write
			STATUS current
			DESCRIPTION
				"Description."
			::= { loopBackDetectionPortConfigEntry 6 }

		
		-- 1.3.6.1.4.1.34592.1.3.100.10.2.1.7
		loopBackDetectionPortStatus OBJECT-TYPE
			SYNTAX INTEGER
				{
				detected(1),
				undetected(2)
				}
			MAX-ACCESS read-only
			STATUS current
			DESCRIPTION
				"Description."
			::= { loopBackDetectionPortConfigEntry 7 }

		
		-- 1.3.6.1.4.1.34592.1.3.100.10.2.1.8
		loopBackDetectionPortConfigAutoRecoverEnable OBJECT-TYPE
			SYNTAX INTEGER
				{
				disable(0),
				enable(1)
				}
			MAX-ACCESS read-write
			STATUS current
			DESCRIPTION
				"Description."
			::= { loopBackDetectionPortConfigEntry 8 }

		
		-- 1.3.6.1.4.1.34592.1.3.100.10.2.1.9
		loopBackDetectionPortConfigAutoRecoverTime OBJECT-TYPE
			SYNTAX INTEGER (20..1200)
			MAX-ACCESS read-write
			STATUS current
			DESCRIPTION
				"Description."
			::= { loopBackDetectionPortConfigEntry 9 }

		
		-- 1.3.6.1.4.1.34592.1.3.100.11
		igmpMemberPortObjects OBJECT IDENTIFIER ::= { nscrtvPonTreeExt 11 }

		
		-- 1.3.6.1.4.1.34592.1.3.100.11.1
		igmpMemberPortTable OBJECT-TYPE
			SYNTAX SEQUENCE OF IgmpMemberPortEntry
			MAX-ACCESS not-accessible
			STATUS current
			DESCRIPTION
				"Description."
			::= { igmpMemberPortObjects 1 }

		
		-- 1.3.6.1.4.1.34592.1.3.100.11.1.1
		igmpMemberPortEntry OBJECT-TYPE
			SYNTAX IgmpMemberPortEntry
			MAX-ACCESS not-accessible
			STATUS current
			DESCRIPTION
				"Description."
			INDEX { igmpMemberPortVid, igmpMemberPortDeviceIndex }
			::= { igmpMemberPortTable 1 }

		
		IgmpMemberPortEntry ::=
			SEQUENCE { 
				igmpMemberPortVid
					INTEGER,
				igmpMemberPortDeviceIndex
					NscrtvPonExtDeviceIndex,
				igmpMemberPortRowStatus
					INTEGER
			 }

		-- 1.3.6.1.4.1.34592.1.3.100.11.1.1.1
		igmpMemberPortVid OBJECT-TYPE
			SYNTAX INTEGER (1..4094)
			MAX-ACCESS not-accessible
			STATUS current
			DESCRIPTION
				"Description."
			::= { igmpMemberPortEntry 1 }

		
		-- 1.3.6.1.4.1.34592.1.3.100.11.1.1.2
		igmpMemberPortDeviceIndex OBJECT-TYPE
			SYNTAX NscrtvPonExtDeviceIndex
			MAX-ACCESS not-accessible
			STATUS current
			DESCRIPTION
				"Description."
			::= { igmpMemberPortEntry 2 }

		
		-- 1.3.6.1.4.1.34592.1.3.100.11.1.1.3
		igmpMemberPortRowStatus OBJECT-TYPE
			SYNTAX INTEGER
			MAX-ACCESS read-create
			STATUS current
			DESCRIPTION
				"Description."
			::= { igmpMemberPortEntry 3 }

		
		-- 1.3.6.1.4.1.34592.1.3.100.12
		onuObjects OBJECT IDENTIFIER ::= { nscrtvPonTreeExt 12 }

		
		-- 1.3.6.1.4.1.34592.1.3.100.12.1
		onuVoiceManagementObjects OBJECT IDENTIFIER ::= { onuObjects 1 }

		
		-- 1.3.6.1.4.1.34592.1.3.100.12.1.1
		onuIadInfoTable OBJECT-TYPE
			SYNTAX SEQUENCE OF OnuIadInfoEntry
			MAX-ACCESS not-accessible
			STATUS current
			DESCRIPTION
				"Description."
			::= { onuVoiceManagementObjects 1 }

		
		-- 1.3.6.1.4.1.34592.1.3.100.12.1.1.1
		onuIadInfoEntry OBJECT-TYPE
			SYNTAX OnuIadInfoEntry
			MAX-ACCESS not-accessible
			STATUS current
			DESCRIPTION
				"Description."
			INDEX { onuIadInfoDeviceIndex }
			::= { onuIadInfoTable 1 }

		
		OnuIadInfoEntry ::=
			SEQUENCE { 
				onuIadInfoDeviceIndex
					NscrtvPonExtDeviceIndex,
				onuIadMac
					MacAddress,
				onuIadProtocol
					INTEGER,
				onuIadSwVersion
					OCTET STRING,
				onuIadSwTime
					OCTET STRING,
				onuIadVoipNum
					Integer32,
				onuIadVoiceFaxMode
					INTEGER,
				onuIadVoiceFaxControl
					INTEGER,
				onuIadOperation
					INTEGER,
				onuIadOperStatus
					INTEGER
			 }

		-- 1.3.6.1.4.1.34592.1.3.100.12.1.1.1.1
		onuIadInfoDeviceIndex OBJECT-TYPE
			SYNTAX NscrtvPonExtDeviceIndex
			MAX-ACCESS not-accessible
			STATUS current
			DESCRIPTION
				"Description."
			::= { onuIadInfoEntry 1 }

		
		-- 1.3.6.1.4.1.34592.1.3.100.12.1.1.1.2
		onuIadMac OBJECT-TYPE
			SYNTAX MacAddress
			MAX-ACCESS read-only
			STATUS current
			DESCRIPTION
				"Description."
			::= { onuIadInfoEntry 2 }

		
		-- 1.3.6.1.4.1.34592.1.3.100.12.1.1.1.3
		onuIadProtocol OBJECT-TYPE
			SYNTAX INTEGER
				{
				h248(0),
				sip(1)
				}
			MAX-ACCESS read-only
			STATUS current
			DESCRIPTION
				"Description."
			::= { onuIadInfoEntry 3 }

		
		-- 1.3.6.1.4.1.34592.1.3.100.12.1.1.1.4
		onuIadSwVersion OBJECT-TYPE
			SYNTAX OCTET STRING (SIZE (0..32))
			MAX-ACCESS read-only
			STATUS current
			DESCRIPTION
				"Description."
			::= { onuIadInfoEntry 4 }

		
		-- 1.3.6.1.4.1.34592.1.3.100.12.1.1.1.5
		onuIadSwTime OBJECT-TYPE
			SYNTAX OCTET STRING (SIZE (0..32))
			MAX-ACCESS read-only
			STATUS current
			DESCRIPTION
				"Description."
			::= { onuIadInfoEntry 5 }

		
		-- 1.3.6.1.4.1.34592.1.3.100.12.1.1.1.6
		onuIadVoipNum OBJECT-TYPE
			SYNTAX Integer32
			MAX-ACCESS read-only
			STATUS current
			DESCRIPTION
				"Description."
			::= { onuIadInfoEntry 6 }

		
		-- 1.3.6.1.4.1.34592.1.3.100.12.1.1.1.7
		onuIadVoiceFaxMode OBJECT-TYPE
			SYNTAX INTEGER
				{
				t30(0),
				t38(1)
				}
			MAX-ACCESS read-write
			STATUS current
			DESCRIPTION
				"Description."
			::= { onuIadInfoEntry 7 }

		
		-- 1.3.6.1.4.1.34592.1.3.100.12.1.1.1.8
		onuIadVoiceFaxControl OBJECT-TYPE
			SYNTAX INTEGER
				{
				negotiation(0),
				autoVBD(1)
				}
			MAX-ACCESS read-write
			STATUS current
			DESCRIPTION
				"Description."
			::= { onuIadInfoEntry 8 }

		
		-- 1.3.6.1.4.1.34592.1.3.100.12.1.1.1.9
		onuIadOperation OBJECT-TYPE
			SYNTAX INTEGER
				{
				reregister(0),
				logout(1),
				reset(2)
				}
			MAX-ACCESS read-write
			STATUS current
			DESCRIPTION
				"Description."
			::= { onuIadInfoEntry 9 }

		
		-- 1.3.6.1.4.1.34592.1.3.100.12.1.1.1.10
		onuIadOperStatus OBJECT-TYPE
			SYNTAX INTEGER
				{
				registering(0),
				regSuccess(1),
				iadFault(2),
				logout(3),
				iadRestarting(4)
				}
			MAX-ACCESS read-only
			STATUS current
			DESCRIPTION
				"Description."
			::= { onuIadInfoEntry 10 }

		
		-- 1.3.6.1.4.1.34592.1.3.100.12.1.2
		onuIadParamCfgTable OBJECT-TYPE
			SYNTAX SEQUENCE OF OnuIadParamCfgEntry
			MAX-ACCESS not-accessible
			STATUS current
			DESCRIPTION
				"Description."
			::= { onuVoiceManagementObjects 2 }

		
		-- 1.3.6.1.4.1.34592.1.3.100.12.1.2.1
		onuIadParamCfgEntry OBJECT-TYPE
			SYNTAX OnuIadParamCfgEntry
			MAX-ACCESS not-accessible
			STATUS current
			DESCRIPTION
				"Description."
			INDEX { onuIadParamCfgDeviceIndex }
			::= { onuIadParamCfgTable 1 }

		
		OnuIadParamCfgEntry ::=
			SEQUENCE { 
				onuIadParamCfgDeviceIndex
					NscrtvPonExtDeviceIndex,
				onuIadMode
					INTEGER,
				onuIadIpAddr
					IpAddress,
				onuIadNetMask
					IpAddress,
				onuIadDefaultGw
					IpAddress,
				onuIadPppoeMode
					INTEGER,
				onuIadPppoeUsrnm
					OCTET STRING,
				onuIadPppoePw
					OCTET STRING,
				onuIadTagMode
					INTEGER,
				onuIadVoiceCVlan
					Integer32,
				onuIadVoiceSVlan
					Integer32,
				onuIadVoicePriority
					Integer32
			 }

		-- 1.3.6.1.4.1.34592.1.3.100.12.1.2.1.1
		onuIadParamCfgDeviceIndex OBJECT-TYPE
			SYNTAX NscrtvPonExtDeviceIndex
			MAX-ACCESS not-accessible
			STATUS current
			DESCRIPTION
				"Description."
			::= { onuIadParamCfgEntry 1 }

		
		-- 1.3.6.1.4.1.34592.1.3.100.12.1.2.1.2
		onuIadMode OBJECT-TYPE
			SYNTAX INTEGER
				{
				static(0),
				dhcp(1),
				pppoe(2)
				}
			MAX-ACCESS read-write
			STATUS current
			DESCRIPTION
				"Description."
			::= { onuIadParamCfgEntry 2 }

		
		-- 1.3.6.1.4.1.34592.1.3.100.12.1.2.1.3
		onuIadIpAddr OBJECT-TYPE
			SYNTAX IpAddress
			MAX-ACCESS read-write
			STATUS current
			DESCRIPTION
				"Description."
			::= { onuIadParamCfgEntry 3 }

		
		-- 1.3.6.1.4.1.34592.1.3.100.12.1.2.1.4
		onuIadNetMask OBJECT-TYPE
			SYNTAX IpAddress
			MAX-ACCESS read-write
			STATUS current
			DESCRIPTION
				"Description."
			::= { onuIadParamCfgEntry 4 }

		
		-- 1.3.6.1.4.1.34592.1.3.100.12.1.2.1.5
		onuIadDefaultGw OBJECT-TYPE
			SYNTAX IpAddress
			MAX-ACCESS read-write
			STATUS current
			DESCRIPTION
				"Description."
			::= { onuIadParamCfgEntry 5 }

		
		-- 1.3.6.1.4.1.34592.1.3.100.12.1.2.1.6
		onuIadPppoeMode OBJECT-TYPE
			SYNTAX INTEGER
				{
				auto(0),
				chap(1),
				pap(2)
				}
			MAX-ACCESS read-write
			STATUS current
			DESCRIPTION
				"Description."
			::= { onuIadParamCfgEntry 6 }

		
		-- 1.3.6.1.4.1.34592.1.3.100.12.1.2.1.7
		onuIadPppoeUsrnm OBJECT-TYPE
			SYNTAX OCTET STRING (SIZE (0..32))
			MAX-ACCESS read-write
			STATUS current
			DESCRIPTION
				"Description."
			::= { onuIadParamCfgEntry 7 }

		
		-- 1.3.6.1.4.1.34592.1.3.100.12.1.2.1.8
		onuIadPppoePw OBJECT-TYPE
			SYNTAX OCTET STRING (SIZE (0..32))
			MAX-ACCESS read-write
			STATUS current
			DESCRIPTION
				"Description."
			::= { onuIadParamCfgEntry 8 }

		
		-- 1.3.6.1.4.1.34592.1.3.100.12.1.2.1.9
		onuIadTagMode OBJECT-TYPE
			SYNTAX INTEGER
				{
				passThrough(0),
				tag(1),
				vlanStack(2)
				}
			MAX-ACCESS read-write
			STATUS current
			DESCRIPTION
				"Description."
			::= { onuIadParamCfgEntry 9 }

		
		-- 1.3.6.1.4.1.34592.1.3.100.12.1.2.1.10
		onuIadVoiceCVlan OBJECT-TYPE
			SYNTAX Integer32 (0..4094)
			MAX-ACCESS read-write
			STATUS current
			DESCRIPTION
				"Description."
			::= { onuIadParamCfgEntry 10 }

		
		-- 1.3.6.1.4.1.34592.1.3.100.12.1.2.1.11
		onuIadVoiceSVlan OBJECT-TYPE
			SYNTAX Integer32 (0..4094)
			MAX-ACCESS read-write
			STATUS current
			DESCRIPTION
				"Description."
			::= { onuIadParamCfgEntry 11 }

		
		-- 1.3.6.1.4.1.34592.1.3.100.12.1.2.1.12
		onuIadVoicePriority OBJECT-TYPE
			SYNTAX Integer32 (0..7)
			MAX-ACCESS read-write
			STATUS current
			DESCRIPTION
				"Description."
			::= { onuIadParamCfgEntry 12 }

		
		-- 1.3.6.1.4.1.34592.1.3.100.12.1.3
		onuIadH248Mangement OBJECT IDENTIFIER ::= { onuVoiceManagementObjects 3 }

		
		-- 1.3.6.1.4.1.34592.1.3.100.12.1.3.1
		h248ParamCfgTable OBJECT-TYPE
			SYNTAX SEQUENCE OF H248ParamCfgEntry
			MAX-ACCESS not-accessible
			STATUS current
			DESCRIPTION
				"Description."
			::= { onuIadH248Mangement 1 }

		
		-- 1.3.6.1.4.1.34592.1.3.100.12.1.3.1.1
		h248ParamCfgEntry OBJECT-TYPE
			SYNTAX H248ParamCfgEntry
			MAX-ACCESS not-accessible
			STATUS current
			DESCRIPTION
				"Description."
			INDEX { h248ParamCfgDeviceIndex }
			::= { h248ParamCfgTable 1 }

		
		H248ParamCfgEntry ::=
			SEQUENCE { 
				h248ParamCfgDeviceIndex
					NscrtvPonExtDeviceIndex,
				h248MgPort
					Integer32,
				h248MgcIp
					IpAddress,
				h248MgcPort
					Integer32,
				h248BakMacIp
					IpAddress,
				h248BakMgcPort
					Integer32,
				h248ActiveMgc
					INTEGER,
				h248RegMode
					INTEGER,
				h248MID
					OCTET STRING,
				h248HbMode
					INTEGER,
				h248HbCycle
					Integer32,
				h248HbCount
					Integer32
			 }

		-- 1.3.6.1.4.1.34592.1.3.100.12.1.3.1.1.1
		h248ParamCfgDeviceIndex OBJECT-TYPE
			SYNTAX NscrtvPonExtDeviceIndex
			MAX-ACCESS not-accessible
			STATUS current
			DESCRIPTION
				"Description."
			::= { h248ParamCfgEntry 1 }

		
		-- 1.3.6.1.4.1.34592.1.3.100.12.1.3.1.1.2
		h248MgPort OBJECT-TYPE
			SYNTAX Integer32 (1024..65535)
			MAX-ACCESS read-write
			STATUS current
			DESCRIPTION
				"Description."
			::= { h248ParamCfgEntry 2 }

		
		-- 1.3.6.1.4.1.34592.1.3.100.12.1.3.1.1.3
		h248MgcIp OBJECT-TYPE
			SYNTAX IpAddress
			MAX-ACCESS read-write
			STATUS current
			DESCRIPTION
				"Description."
			::= { h248ParamCfgEntry 3 }

		
		-- 1.3.6.1.4.1.34592.1.3.100.12.1.3.1.1.4
		h248MgcPort OBJECT-TYPE
			SYNTAX Integer32 (1024..65535)
			MAX-ACCESS read-write
			STATUS current
			DESCRIPTION
				"Description."
			::= { h248ParamCfgEntry 4 }

		
		-- 1.3.6.1.4.1.34592.1.3.100.12.1.3.1.1.5
		h248BakMacIp OBJECT-TYPE
			SYNTAX IpAddress
			MAX-ACCESS read-write
			STATUS current
			DESCRIPTION
				"Description."
			::= { h248ParamCfgEntry 5 }

		
		-- 1.3.6.1.4.1.34592.1.3.100.12.1.3.1.1.6
		h248BakMgcPort OBJECT-TYPE
			SYNTAX Integer32 (1024..65535)
			MAX-ACCESS read-write
			STATUS current
			DESCRIPTION
				"Description."
			::= { h248ParamCfgEntry 6 }

		
		-- 1.3.6.1.4.1.34592.1.3.100.12.1.3.1.1.7
		h248ActiveMgc OBJECT-TYPE
			SYNTAX INTEGER
				{
				backup(0),
				active(1)
				}
			MAX-ACCESS read-only
			STATUS current
			DESCRIPTION
				"Description."
			::= { h248ParamCfgEntry 7 }

		
		-- 1.3.6.1.4.1.34592.1.3.100.12.1.3.1.1.8
		h248RegMode OBJECT-TYPE
			SYNTAX INTEGER
				{
				ipAddress(0),
				domainName(1),
				deviceName(2)
				}
			MAX-ACCESS read-write
			STATUS current
			DESCRIPTION
				"Description."
			::= { h248ParamCfgEntry 8 }

		
		-- 1.3.6.1.4.1.34592.1.3.100.12.1.3.1.1.9
		h248MID OBJECT-TYPE
			SYNTAX OCTET STRING (SIZE (0..64))
			MAX-ACCESS read-write
			STATUS current
			DESCRIPTION
				"Description."
			::= { h248ParamCfgEntry 9 }

		
		-- 1.3.6.1.4.1.34592.1.3.100.12.1.3.1.1.10
		h248HbMode OBJECT-TYPE
			SYNTAX INTEGER
				{
				close(0),
				h248ctc(1)
				}
			MAX-ACCESS read-write
			STATUS current
			DESCRIPTION
				"Description."
			::= { h248ParamCfgEntry 10 }

		
		-- 1.3.6.1.4.1.34592.1.3.100.12.1.3.1.1.11
		h248HbCycle OBJECT-TYPE
			SYNTAX Integer32 (10..600)
			MAX-ACCESS read-write
			STATUS current
			DESCRIPTION
				"Description."
			::= { h248ParamCfgEntry 11 }

		
		-- 1.3.6.1.4.1.34592.1.3.100.12.1.3.1.1.12
		h248HbCount OBJECT-TYPE
			SYNTAX Integer32 (1..10)
			MAX-ACCESS read-write
			STATUS current
			DESCRIPTION
				"Description."
			::= { h248ParamCfgEntry 12 }

		
		-- 1.3.6.1.4.1.34592.1.3.100.12.1.3.2
		h248RtpTIDInfoTable OBJECT-TYPE
			SYNTAX SEQUENCE OF H248RtpTIDInfoEntry
			MAX-ACCESS not-accessible
			STATUS current
			DESCRIPTION
				"Description."
			::= { onuIadH248Mangement 2 }

		
		-- 1.3.6.1.4.1.34592.1.3.100.12.1.3.2.1
		h248RtpTIDInfoEntry OBJECT-TYPE
			SYNTAX H248RtpTIDInfoEntry
			MAX-ACCESS not-accessible
			STATUS current
			DESCRIPTION
				"Description."
			INDEX { h248RtpTIDInfoDeviceIndex }
			::= { h248RtpTIDInfoTable 1 }

		
		H248RtpTIDInfoEntry ::=
			SEQUENCE { 
				h248RtpTIDInfoDeviceIndex
					NscrtvPonExtDeviceIndex,
				h248RtpTIDCount
					Integer32,
				h248FstRtpTIDName
					OCTET STRING,
				h248RtpTIDNum
					Integer32,
				h248RtpTIDPrefix
					OCTET STRING,
				h248RtpTIDDigitBegin
					Integer32,
				h248RtpTIDMode
					INTEGER,
				h248RtpTIDDigitLen
					Integer32
			 }

		-- 1.3.6.1.4.1.34592.1.3.100.12.1.3.2.1.1
		h248RtpTIDInfoDeviceIndex OBJECT-TYPE
			SYNTAX NscrtvPonExtDeviceIndex
			MAX-ACCESS not-accessible
			STATUS current
			DESCRIPTION
				"Description."
			::= { h248RtpTIDInfoEntry 1 }

		
		-- 1.3.6.1.4.1.34592.1.3.100.12.1.3.2.1.2
		h248RtpTIDCount OBJECT-TYPE
			SYNTAX Integer32 (0..255)
			MAX-ACCESS read-only
			STATUS current
			DESCRIPTION
				"Description."
			::= { h248RtpTIDInfoEntry 2 }

		
		-- 1.3.6.1.4.1.34592.1.3.100.12.1.3.2.1.3
		h248FstRtpTIDName OBJECT-TYPE
			SYNTAX OCTET STRING (SIZE (0..32))
			MAX-ACCESS read-only
			STATUS current
			DESCRIPTION
				"Description."
			::= { h248RtpTIDInfoEntry 3 }

		
		-- 1.3.6.1.4.1.34592.1.3.100.12.1.3.2.1.4
		h248RtpTIDNum OBJECT-TYPE
			SYNTAX Integer32 (1..10)
			MAX-ACCESS read-write
			STATUS current
			DESCRIPTION
				"Description."
			::= { h248RtpTIDInfoEntry 4 }

		
		-- 1.3.6.1.4.1.34592.1.3.100.12.1.3.2.1.5
		h248RtpTIDPrefix OBJECT-TYPE
			SYNTAX OCTET STRING (SIZE (0..16))
			MAX-ACCESS read-write
			STATUS current
			DESCRIPTION
				"Description."
			::= { h248RtpTIDInfoEntry 5 }

		
		-- 1.3.6.1.4.1.34592.1.3.100.12.1.3.2.1.6
		h248RtpTIDDigitBegin OBJECT-TYPE
			SYNTAX Integer32
			MAX-ACCESS read-write
			STATUS current
			DESCRIPTION
				"Description."
			::= { h248RtpTIDInfoEntry 6 }

		
		-- 1.3.6.1.4.1.34592.1.3.100.12.1.3.2.1.7
		h248RtpTIDMode OBJECT-TYPE
			SYNTAX INTEGER
				{
				align(0),
				nonAlign(1)
				}
			MAX-ACCESS read-write
			STATUS current
			DESCRIPTION
				"Description."
			::= { h248RtpTIDInfoEntry 7 }

		
		-- 1.3.6.1.4.1.34592.1.3.100.12.1.3.2.1.8
		h248RtpTIDDigitLen OBJECT-TYPE
			SYNTAX Integer32 (1..8)
			MAX-ACCESS read-write
			STATUS current
			DESCRIPTION
				"Description."
			::= { h248RtpTIDInfoEntry 8 }

		
		-- 1.3.6.1.4.1.34592.1.3.100.12.1.3.3
		h248UserTIDTable OBJECT-TYPE
			SYNTAX SEQUENCE OF H248UserTIDEntry
			MAX-ACCESS not-accessible
			STATUS current
			DESCRIPTION
				"Description."
			::= { onuIadH248Mangement 3 }

		
		-- 1.3.6.1.4.1.34592.1.3.100.12.1.3.3.1
		h248UserTIDEntry OBJECT-TYPE
			SYNTAX H248UserTIDEntry
			MAX-ACCESS not-accessible
			STATUS current
			DESCRIPTION
				"Description."
			INDEX { h248UserTIDDeviceIndex, h248UserTIDCardIndex, h248UserTIDPortIndex }
			::= { h248UserTIDTable 1 }

		
		H248UserTIDEntry ::=
			SEQUENCE { 
				h248UserTIDDeviceIndex
					NscrtvPonExtDeviceIndex,
				h248UserTIDCardIndex
					NscrtvPonExtCardIndex,
				h248UserTIDPortIndex
					NscrtvPonPortIndex,
				h248UserTIDName
					OCTET STRING
			 }

		-- 1.3.6.1.4.1.34592.1.3.100.12.1.3.3.1.1
		h248UserTIDDeviceIndex OBJECT-TYPE
			SYNTAX NscrtvPonExtDeviceIndex
			MAX-ACCESS not-accessible
			STATUS current
			DESCRIPTION
				"Description."
			::= { h248UserTIDEntry 1 }

		
		-- 1.3.6.1.4.1.34592.1.3.100.12.1.3.3.1.2
		h248UserTIDCardIndex OBJECT-TYPE
			SYNTAX NscrtvPonExtCardIndex
			MAX-ACCESS not-accessible
			STATUS current
			DESCRIPTION
				"Description."
			::= { h248UserTIDEntry 2 }

		
		-- 1.3.6.1.4.1.34592.1.3.100.12.1.3.3.1.3
		h248UserTIDPortIndex OBJECT-TYPE
			SYNTAX NscrtvPonPortIndex
			MAX-ACCESS not-accessible
			STATUS current
			DESCRIPTION
				"Description."
			::= { h248UserTIDEntry 3 }

		
		-- 1.3.6.1.4.1.34592.1.3.100.12.1.3.3.1.4
		h248UserTIDName OBJECT-TYPE
			SYNTAX OCTET STRING (SIZE (0..32))
			MAX-ACCESS read-write
			STATUS current
			DESCRIPTION
				"Description."
			::= { h248UserTIDEntry 4 }

		
		-- 1.3.6.1.4.1.34592.1.3.100.12.1.4
		onuIadSipMangement OBJECT IDENTIFIER ::= { onuVoiceManagementObjects 4 }

		
		-- 1.3.6.1.4.1.34592.1.3.100.12.1.4.1
		sipParamCfgTable OBJECT-TYPE
			SYNTAX SEQUENCE OF SipParamCfgEntry
			MAX-ACCESS not-accessible
			STATUS current
			DESCRIPTION
				"Description."
			::= { onuIadSipMangement 1 }

		
		-- 1.3.6.1.4.1.34592.1.3.100.12.1.4.1.1
		sipParamCfgEntry OBJECT-TYPE
			SYNTAX SipParamCfgEntry
			MAX-ACCESS not-accessible
			STATUS current
			DESCRIPTION
				"Description."
			INDEX { sipParamCfgDeviceIndex }
			::= { sipParamCfgTable 1 }

		
		SipParamCfgEntry ::=
			SEQUENCE { 
				sipParamCfgDeviceIndex
					NscrtvPonExtDeviceIndex,
				sipMgPort
					Integer32,
				sipProxySvrIp
					IpAddress,
				sipProxySvrPort
					Integer32,
				sipBakProxySvrIp
					IpAddress,
				sipBakProxySvrPort
					Integer32,
				sipActiveProxySvr
					IpAddress,
				sipRegSvrIp
					IpAddress,
				sipRegSvrPort
					Integer32,
				sipBakRegSvrIp
					IpAddress,
				sipBakRegSvrPort
					Integer32,
				sipOutBoundSvrIp
					IpAddress,
				sipOutBoundSvrPort
					Integer32,
				sipRegInterval
					Integer32,
				sipHbSwitch
					INTEGER,
				sipHbCycle
					Integer32,
				sipHbCount
					Integer32,
				sipDigitMap
					OCTET STRING
			 }

		-- 1.3.6.1.4.1.34592.1.3.100.12.1.4.1.1.1
		sipParamCfgDeviceIndex OBJECT-TYPE
			SYNTAX NscrtvPonExtDeviceIndex
			MAX-ACCESS not-accessible
			STATUS current
			DESCRIPTION
				"Description."
			::= { sipParamCfgEntry 1 }

		
		-- 1.3.6.1.4.1.34592.1.3.100.12.1.4.1.1.2
		sipMgPort OBJECT-TYPE
			SYNTAX Integer32 (1024..65535)
			MAX-ACCESS read-write
			STATUS current
			DESCRIPTION
				"Description."
			::= { sipParamCfgEntry 2 }

		
		-- 1.3.6.1.4.1.34592.1.3.100.12.1.4.1.1.3
		sipProxySvrIp OBJECT-TYPE
			SYNTAX IpAddress
			MAX-ACCESS read-write
			STATUS current
			DESCRIPTION
				"Description."
			::= { sipParamCfgEntry 3 }

		
		-- 1.3.6.1.4.1.34592.1.3.100.12.1.4.1.1.4
		sipProxySvrPort OBJECT-TYPE
			SYNTAX Integer32 (1024..65535)
			MAX-ACCESS read-write
			STATUS current
			DESCRIPTION
				"Description."
			::= { sipParamCfgEntry 4 }

		
		-- 1.3.6.1.4.1.34592.1.3.100.12.1.4.1.1.5
		sipBakProxySvrIp OBJECT-TYPE
			SYNTAX IpAddress
			MAX-ACCESS read-write
			STATUS current
			DESCRIPTION
				"Description."
			::= { sipParamCfgEntry 5 }

		
		-- 1.3.6.1.4.1.34592.1.3.100.12.1.4.1.1.6
		sipBakProxySvrPort OBJECT-TYPE
			SYNTAX Integer32 (1024..65535)
			MAX-ACCESS read-write
			STATUS current
			DESCRIPTION
				"Description."
			::= { sipParamCfgEntry 6 }

		
		-- 1.3.6.1.4.1.34592.1.3.100.12.1.4.1.1.7
		sipActiveProxySvr OBJECT-TYPE
			SYNTAX IpAddress
			MAX-ACCESS read-only
			STATUS current
			DESCRIPTION
				"Description."
			::= { sipParamCfgEntry 7 }

		
		-- 1.3.6.1.4.1.34592.1.3.100.12.1.4.1.1.8
		sipRegSvrIp OBJECT-TYPE
			SYNTAX IpAddress
			MAX-ACCESS read-write
			STATUS current
			DESCRIPTION
				"Description."
			::= { sipParamCfgEntry 8 }

		
		-- 1.3.6.1.4.1.34592.1.3.100.12.1.4.1.1.9
		sipRegSvrPort OBJECT-TYPE
			SYNTAX Integer32 (1024..65535)
			MAX-ACCESS read-write
			STATUS current
			DESCRIPTION
				"Description."
			::= { sipParamCfgEntry 9 }

		
		-- 1.3.6.1.4.1.34592.1.3.100.12.1.4.1.1.10
		sipBakRegSvrIp OBJECT-TYPE
			SYNTAX IpAddress
			MAX-ACCESS read-write
			STATUS current
			DESCRIPTION
				"Description."
			::= { sipParamCfgEntry 10 }

		
		-- 1.3.6.1.4.1.34592.1.3.100.12.1.4.1.1.11
		sipBakRegSvrPort OBJECT-TYPE
			SYNTAX Integer32 (1024..65535)
			MAX-ACCESS read-write
			STATUS current
			DESCRIPTION
				"Description."
			::= { sipParamCfgEntry 11 }

		
		-- 1.3.6.1.4.1.34592.1.3.100.12.1.4.1.1.12
		sipOutBoundSvrIp OBJECT-TYPE
			SYNTAX IpAddress
			MAX-ACCESS read-write
			STATUS current
			DESCRIPTION
				"Description."
			::= { sipParamCfgEntry 12 }

		
		-- 1.3.6.1.4.1.34592.1.3.100.12.1.4.1.1.13
		sipOutBoundSvrPort OBJECT-TYPE
			SYNTAX Integer32 (1024..65535)
			MAX-ACCESS read-write
			STATUS current
			DESCRIPTION
				"Description."
			::= { sipParamCfgEntry 13 }

		
		-- 1.3.6.1.4.1.34592.1.3.100.12.1.4.1.1.14
		sipRegInterval OBJECT-TYPE
			SYNTAX Integer32
			MAX-ACCESS read-write
			STATUS current
			DESCRIPTION
				"Description."
			::= { sipParamCfgEntry 14 }

		
		-- 1.3.6.1.4.1.34592.1.3.100.12.1.4.1.1.15
		sipHbSwitch OBJECT-TYPE
			SYNTAX INTEGER
				{
				enable(0),
				disable(1)
				}
			MAX-ACCESS read-write
			STATUS current
			DESCRIPTION
				"Description."
			::= { sipParamCfgEntry 15 }

		
		-- 1.3.6.1.4.1.34592.1.3.100.12.1.4.1.1.16
		sipHbCycle OBJECT-TYPE
			SYNTAX Integer32 (10..600)
			MAX-ACCESS read-write
			STATUS current
			DESCRIPTION
				"Description."
			::= { sipParamCfgEntry 16 }

		
		-- 1.3.6.1.4.1.34592.1.3.100.12.1.4.1.1.17
		sipHbCount OBJECT-TYPE
			SYNTAX Integer32 (1..10)
			MAX-ACCESS read-write
			STATUS current
			DESCRIPTION
				"Description."
			::= { sipParamCfgEntry 17 }

		
		-- 1.3.6.1.4.1.34592.1.3.100.12.1.4.1.1.18
		sipDigitMap OBJECT-TYPE
			SYNTAX OCTET STRING (SIZE (0..1000))
			MAX-ACCESS read-write
			STATUS current
			DESCRIPTION
				"Description."
			::= { sipParamCfgEntry 18 }

		
		-- 1.3.6.1.4.1.34592.1.3.100.12.1.4.2
		sipUserCfgTable OBJECT-TYPE
			SYNTAX SEQUENCE OF SipUserCfgEntry
			MAX-ACCESS not-accessible
			STATUS current
			DESCRIPTION
				"Description."
			::= { onuIadSipMangement 2 }

		
		-- 1.3.6.1.4.1.34592.1.3.100.12.1.4.2.1
		sipUserCfgEntry OBJECT-TYPE
			SYNTAX SipUserCfgEntry
			MAX-ACCESS not-accessible
			STATUS current
			DESCRIPTION
				"Description."
			INDEX { sipUserCfgDeviceIndex, sipUserCfgCardIndex, sipUserCfgPotsIndex }
			::= { sipUserCfgTable 1 }

		
		SipUserCfgEntry ::=
			SEQUENCE { 
				sipUserCfgDeviceIndex
					NscrtvPonExtDeviceIndex,
				sipUserCfgCardIndex
					NscrtvPonExtCardIndex,
				sipUserCfgPotsIndex
					NscrtvPonPortIndex,
				sipUserAccount
					OCTET STRING,
				sipUserName
					OCTET STRING,
				sipUserPasswd
					OCTET STRING
			 }

		-- 1.3.6.1.4.1.34592.1.3.100.12.1.4.2.1.1
		sipUserCfgDeviceIndex OBJECT-TYPE
			SYNTAX NscrtvPonExtDeviceIndex
			MAX-ACCESS not-accessible
			STATUS current
			DESCRIPTION
				"Description."
			::= { sipUserCfgEntry 1 }

		
		-- 1.3.6.1.4.1.34592.1.3.100.12.1.4.2.1.2
		sipUserCfgCardIndex OBJECT-TYPE
			SYNTAX NscrtvPonExtCardIndex
			MAX-ACCESS not-accessible
			STATUS current
			DESCRIPTION
				"Description."
			::= { sipUserCfgEntry 2 }

		
		-- 1.3.6.1.4.1.34592.1.3.100.12.1.4.2.1.3
		sipUserCfgPotsIndex OBJECT-TYPE
			SYNTAX NscrtvPonPortIndex
			MAX-ACCESS not-accessible
			STATUS current
			DESCRIPTION
				"Description."
			::= { sipUserCfgEntry 3 }

		
		-- 1.3.6.1.4.1.34592.1.3.100.12.1.4.2.1.4
		sipUserAccount OBJECT-TYPE
			SYNTAX OCTET STRING (SIZE (0..16))
			MAX-ACCESS read-write
			STATUS current
			DESCRIPTION
				"Description."
			::= { sipUserCfgEntry 4 }

		
		-- 1.3.6.1.4.1.34592.1.3.100.12.1.4.2.1.5
		sipUserName OBJECT-TYPE
			SYNTAX OCTET STRING (SIZE (0..32))
			MAX-ACCESS read-write
			STATUS current
			DESCRIPTION
				"Description."
			::= { sipUserCfgEntry 5 }

		
		-- 1.3.6.1.4.1.34592.1.3.100.12.1.4.2.1.6
		sipUserPasswd OBJECT-TYPE
			SYNTAX OCTET STRING (SIZE (0..16))
			MAX-ACCESS read-write
			STATUS current
			DESCRIPTION
				"Description."
			::= { sipUserCfgEntry 6 }

		
		-- 1.3.6.1.4.1.34592.1.3.100.12.1.5
		onuIadPotsInfoTable OBJECT-TYPE
			SYNTAX SEQUENCE OF OnuIadPotsInfoEntry
			MAX-ACCESS not-accessible
			STATUS current
			DESCRIPTION
				"Description."
			::= { onuVoiceManagementObjects 5 }

		
		-- 1.3.6.1.4.1.34592.1.3.100.12.1.5.1
		onuIadPotsInfoEntry OBJECT-TYPE
			SYNTAX OnuIadPotsInfoEntry
			MAX-ACCESS not-accessible
			STATUS current
			DESCRIPTION
				"Description."
			INDEX { potsInfoDeviceIndex, potsInfoCardIndex, potsInfoPortIndex }
			::= { onuIadPotsInfoTable 1 }

		
		OnuIadPotsInfoEntry ::=
			SEQUENCE { 
				potsInfoDeviceIndex
					NscrtvPonExtDeviceIndex,
				potsInfoCardIndex
					NscrtvPonExtCardIndex,
				potsInfoPortIndex
					NscrtvPonPortIndex,
				onuIadPotsEnable
					INTEGER,
				onuIadPotsStatus
					INTEGER,
				onuIadPotsServiceState
					INTEGER,
				onuIadPotsCodeMode
					INTEGER
			 }

		-- 1.3.6.1.4.1.34592.1.3.100.12.1.5.1.1
		potsInfoDeviceIndex OBJECT-TYPE
			SYNTAX NscrtvPonExtDeviceIndex
			MAX-ACCESS not-accessible
			STATUS current
			DESCRIPTION
				"Description."
			::= { onuIadPotsInfoEntry 1 }

		
		-- 1.3.6.1.4.1.34592.1.3.100.12.1.5.1.2
		potsInfoCardIndex OBJECT-TYPE
			SYNTAX NscrtvPonExtCardIndex
			MAX-ACCESS not-accessible
			STATUS current
			DESCRIPTION
				"Description."
			::= { onuIadPotsInfoEntry 2 }

		
		-- 1.3.6.1.4.1.34592.1.3.100.12.1.5.1.3
		potsInfoPortIndex OBJECT-TYPE
			SYNTAX NscrtvPonPortIndex
			MAX-ACCESS not-accessible
			STATUS current
			DESCRIPTION
				"Description."
			::= { onuIadPotsInfoEntry 3 }

		
		-- 1.3.6.1.4.1.34592.1.3.100.12.1.5.1.4
		onuIadPotsEnable OBJECT-TYPE
			SYNTAX INTEGER
				{
				disable(1),
				enable(2)
				}
			MAX-ACCESS read-write
			STATUS current
			DESCRIPTION
				"Description."
			::= { onuIadPotsInfoEntry 4 }

		
		-- 1.3.6.1.4.1.34592.1.3.100.12.1.5.1.5
		onuIadPotsStatus OBJECT-TYPE
			SYNTAX INTEGER
				{
				registering(0),
				idle(1),
				pickUp(2),
				dialing(3),
				ringing(4),
				ringBack(5),
				connecting(6),
				connected(7),
				releasing(8),
				regFailure(9),
				notActivated(10)
				}
			MAX-ACCESS read-only
			STATUS current
			DESCRIPTION
				"Description."
			::= { onuIadPotsInfoEntry 5 }

		
		-- 1.3.6.1.4.1.34592.1.3.100.12.1.5.1.6
		onuIadPotsServiceState OBJECT-TYPE
			SYNTAX INTEGER
				{
				endLocal(0),
				endRemote(1),
				endAuto(2),
				normal(3)
				}
			MAX-ACCESS read-only
			STATUS current
			DESCRIPTION
				"Description."
			::= { onuIadPotsInfoEntry 6 }

		
		-- 1.3.6.1.4.1.34592.1.3.100.12.1.5.1.7
		onuIadPotsCodeMode OBJECT-TYPE
			SYNTAX INTEGER
				{
				g711a(0),
				g729(1),
				g711u(2),
				g723(3),
				g726(4),
				t38(5)
				}
			MAX-ACCESS read-only
			STATUS current
			DESCRIPTION
				"Description."
			::= { onuIadPotsInfoEntry 7 }

		
		-- 1.3.6.1.4.1.34592.1.3.100.12.2
		onuMacAddressObjects OBJECT IDENTIFIER ::= { onuObjects 2 }

		
		-- 1.3.6.1.4.1.34592.1.3.100.12.2.1
		onuMacAddressTable OBJECT-TYPE
			SYNTAX SEQUENCE OF OnuMacAddressEntry
			MAX-ACCESS not-accessible
			STATUS current
			DESCRIPTION
				"Description."
			::= { onuMacAddressObjects 1 }

		
		-- 1.3.6.1.4.1.34592.1.3.100.12.2.1.1
		onuMacAddressEntry OBJECT-TYPE
			SYNTAX OnuMacAddressEntry
			MAX-ACCESS not-accessible
			STATUS current
			DESCRIPTION
				"Description."
			INDEX { onuMacAddrIndex, onuMacAddrVlanIdIndex }
			::= { onuMacAddressTable 1 }

		
		OnuMacAddressEntry ::=
			SEQUENCE { 
				onuMacAddrIndex
					MacAddress,
				onuMacAddrVlanIdIndex
					Integer32,
				onuMacAddrDeviceIndex
					NscrtvPonExtDeviceIndex,
				onuMacAddr
					MacAddress
			 }

		-- 1.3.6.1.4.1.34592.1.3.100.12.2.1.1.1
		onuMacAddrIndex OBJECT-TYPE
			SYNTAX MacAddress
			MAX-ACCESS not-accessible
			STATUS current
			DESCRIPTION
				"Description."
			::= { onuMacAddressEntry 1 }

		
		-- 1.3.6.1.4.1.34592.1.3.100.12.2.1.1.2
		onuMacAddrVlanIdIndex OBJECT-TYPE
			SYNTAX Integer32
			MAX-ACCESS not-accessible
			STATUS current
			DESCRIPTION
				"Description."
			::= { onuMacAddressEntry 2 }

		
		-- 1.3.6.1.4.1.34592.1.3.100.12.2.1.1.3
		onuMacAddrDeviceIndex OBJECT-TYPE
			SYNTAX NscrtvPonExtDeviceIndex
			MAX-ACCESS read-only
			STATUS current
			DESCRIPTION
				"Description."
			::= { onuMacAddressEntry 3 }

		
		-- 1.3.6.1.4.1.34592.1.3.100.12.2.1.1.4
		onuMacAddr OBJECT-TYPE
			SYNTAX MacAddress
			MAX-ACCESS read-only
			STATUS current
			DESCRIPTION
				"Description."
			::= { onuMacAddressEntry 4 }

		
		-- 1.3.6.1.4.1.34592.1.3.100.12.3
		onuRegInfoObjects OBJECT IDENTIFIER ::= { onuObjects 3 }

		
		-- 1.3.6.1.4.1.34592.1.3.100.12.3.1
		onuRegInfoTable OBJECT-TYPE
			SYNTAX SEQUENCE OF OnuRegInfoEntry
			MAX-ACCESS not-accessible
			STATUS current
			DESCRIPTION
				"Description."
			::= { onuRegInfoObjects 1 }

		
		-- 1.3.6.1.4.1.34592.1.3.100.12.3.1.1
		onuRegInfoEntry OBJECT-TYPE
			SYNTAX OnuRegInfoEntry
			MAX-ACCESS not-accessible
			STATUS current
			DESCRIPTION
				"Description."
			INDEX { onuRegInfoDeviceIndex }
			::= { onuRegInfoTable 1 }

		
		OnuRegInfoEntry ::=
			SEQUENCE { 
				onuRegInfoDeviceIndex
					NscrtvPonExtDeviceIndex,
				onuRegInfoRegTimes
					Unsigned32,
				onuRegInfoDeregTimes
					Unsigned32,
				onuRegInfoOnlineDate
					DateAndTime,
				onuRegInfoOfflineDate
					DateAndTime,
				onuRegInfoOnlineDuration
					Unsigned32,
				onuRegInfoOfflineReason
					OCTET STRING,
				onuRegInfoModelId
					DisplayString,
				onuPortLoopDetectSwitch
					INTEGER,
				onuPortAutoShutdown
					INTEGER,
				onuPortLoopDetectAutoDeactivate
					INTEGER
			 }

		-- 1.3.6.1.4.1.34592.1.3.100.12.3.1.1.1
		onuRegInfoDeviceIndex OBJECT-TYPE
			SYNTAX NscrtvPonExtDeviceIndex
			MAX-ACCESS not-accessible
			STATUS current
			DESCRIPTION
				"Description."
			::= { onuRegInfoEntry 1 }

		
		-- 1.3.6.1.4.1.34592.1.3.100.12.3.1.1.2
		onuRegInfoRegTimes OBJECT-TYPE
			SYNTAX Unsigned32
			MAX-ACCESS read-only
			STATUS current
			DESCRIPTION
				"Description."
			::= { onuRegInfoEntry 2 }

		
		-- 1.3.6.1.4.1.34592.1.3.100.12.3.1.1.3
		onuRegInfoDeregTimes OBJECT-TYPE
			SYNTAX Unsigned32
			MAX-ACCESS read-only
			STATUS current
			DESCRIPTION
				"Description."
			::= { onuRegInfoEntry 3 }

		
		-- 1.3.6.1.4.1.34592.1.3.100.12.3.1.1.4
		onuRegInfoOnlineDate OBJECT-TYPE
			SYNTAX DateAndTime
			MAX-ACCESS read-only
			STATUS current
			DESCRIPTION
				"Description."
			::= { onuRegInfoEntry 4 }

		
		-- 1.3.6.1.4.1.34592.1.3.100.12.3.1.1.5
		onuRegInfoOfflineDate OBJECT-TYPE
			SYNTAX DateAndTime
			MAX-ACCESS read-only
			STATUS current
			DESCRIPTION
				"Description."
			::= { onuRegInfoEntry 5 }

		
		-- 1.3.6.1.4.1.34592.1.3.100.12.3.1.1.6
		onuRegInfoOnlineDuration OBJECT-TYPE
			SYNTAX Unsigned32
			MAX-ACCESS read-only
			STATUS current
			DESCRIPTION
				"Description."
			::= { onuRegInfoEntry 6 }

		
		-- 1.3.6.1.4.1.34592.1.3.100.12.3.1.1.7
		onuRegInfoOfflineReason OBJECT-TYPE
			SYNTAX OCTET STRING
			MAX-ACCESS read-only
			STATUS current
			DESCRIPTION
				"Description."
			::= { onuRegInfoEntry 7 }

		
		-- 1.3.6.1.4.1.34592.1.3.100.12.3.1.1.8
		onuRegInfoModelId OBJECT-TYPE
			SYNTAX DisplayString
			MAX-ACCESS read-only
			STATUS current
			DESCRIPTION
				"Description."
			::= { onuRegInfoEntry 8 }

		
		-- 1.3.6.1.4.1.34592.1.3.100.12.3.1.1.9
		onuPortLoopDetectSwitch OBJECT-TYPE
			SYNTAX INTEGER
				{
				disable(1),
				enable(2)
				}
			MAX-ACCESS read-write
			STATUS current
			DESCRIPTION
				"Description."
			::= { onuRegInfoEntry 9 }

		
		-- 1.3.6.1.4.1.34592.1.3.100.12.3.1.1.10
		onuPortAutoShutdown OBJECT-TYPE
			SYNTAX INTEGER
				{
				disable(0),
				enable(1),
				enableButNoRecovery(2)
				}
			MAX-ACCESS read-write
			STATUS current
			DESCRIPTION
				"Description."
			::= { onuRegInfoEntry 10 }

		
		-- 1.3.6.1.4.1.34592.1.3.100.12.3.1.1.11
		onuPortLoopDetectAutoDeactivate OBJECT-TYPE
			SYNTAX INTEGER
				{
				disable(0),
				enable(1)
				}
			MAX-ACCESS read-write
			STATUS current
			DESCRIPTION
				"Description."
			::= { onuRegInfoEntry 11 }

		
		-- 1.3.6.1.4.1.34592.1.3.100.12.4
		onuUpdateTimerObjects OBJECT IDENTIFIER ::= { onuObjects 4 }

		
		-- 1.3.6.1.4.1.34592.1.3.100.12.4.1
		onuUpdateTimerTable OBJECT-TYPE
			SYNTAX SEQUENCE OF OnuUpdateTimerEntry
			MAX-ACCESS not-accessible
			STATUS current
			DESCRIPTION
				"Description."
			::= { onuUpdateTimerObjects 1 }

		
		-- 1.3.6.1.4.1.34592.1.3.100.12.4.1.1
		onuUpdateTimerEntry OBJECT-TYPE
			SYNTAX OnuUpdateTimerEntry
			MAX-ACCESS not-accessible
			STATUS current
			DESCRIPTION
				"Description."
			INDEX { onuUpdateTimerDeviceIndex }
			::= { onuUpdateTimerTable 1 }

		
		OnuUpdateTimerEntry ::=
			SEQUENCE { 
				onuUpdateTimerDeviceIndex
					NscrtvPonExtDeviceIndex,
				onuUpdateTimerSwitch
					INTEGER,
				onuUpdateTimerImageName
					DisplayString,
				onuUpdateTimerSelectType
					INTEGER,
				onuUpdateTimerModelId
					OCTET STRING,
				onuUpdateTimerPortList
					OCTET STRING,
				onuUpdateTimerOntList
					OCTET STRING,
				onuUpdateTimerSystemTime
					DateAndTime,
				onuUpdateTimerConfigTime
					DateAndTime,
				onuUpdateTimerGlobalStatus
					DisplayString,
				onuUpdateTimerTotalNum
					Unsigned32,
				onuUpdateTimerSuccessNum
					Unsigned32,
				onuUpdateTimerFailureNum
					Unsigned32,
				onuUpdateTimerOntStatus
					OCTET STRING
			 }

		-- 1.3.6.1.4.1.34592.1.3.100.12.4.1.1.1
		onuUpdateTimerDeviceIndex OBJECT-TYPE
			SYNTAX NscrtvPonExtDeviceIndex
			MAX-ACCESS not-accessible
			STATUS current
			DESCRIPTION
				"Description."
			::= { onuUpdateTimerEntry 1 }

		
		-- 1.3.6.1.4.1.34592.1.3.100.12.4.1.1.2
		onuUpdateTimerSwitch OBJECT-TYPE
			SYNTAX INTEGER
				{
				disable(0),
				enable(1)
				}
			MAX-ACCESS read-write
			STATUS current
			DESCRIPTION
				"Description."
			::= { onuUpdateTimerEntry 2 }

		
		-- 1.3.6.1.4.1.34592.1.3.100.12.4.1.1.3
		onuUpdateTimerImageName OBJECT-TYPE
			SYNTAX DisplayString
			MAX-ACCESS read-write
			STATUS current
			DESCRIPTION
				"用于升级ONU的镜像文件名(SIZE:255)."
			::= { onuUpdateTimerEntry 3 }

		
		-- 1.3.6.1.4.1.34592.1.3.100.12.4.1.1.4
		onuUpdateTimerSelectType OBJECT-TYPE
			SYNTAX INTEGER
				{
				oltBased(0),
				modelIdBased(1),
				portBased(2),
				ontBased(3),
				portModelIdBased(4),
				ontModelIdBased(5)
				}
			MAX-ACCESS read-write
			STATUS current
			DESCRIPTION
				"oltBased：默认模式，升级所有ONU，不需配置ModelId、PortList和OntList
				modelIdBased：基于Model ID升级，只需配置ModelId
				portBased：基于PORT级别升级，只需配置PortList
				ontBased：基于ONU级别升级，需配置PortList + OntList	
				portModelIdBased：基于PORT + Model ID升级，需配置ModelId + PortList	
				ontModelIdBased：基于ONU + Model ID升级，需配置ModelId + PortList + OntList					 
				"
			::= { onuUpdateTimerEntry 4 }

		
		-- 1.3.6.1.4.1.34592.1.3.100.12.4.1.1.5
		onuUpdateTimerModelId OBJECT-TYPE
			SYNTAX OCTET STRING
			MAX-ACCESS read-write
			STATUS current
			DESCRIPTION
				"Hexadecimal model ID(SIZE:4).(e.g.:0x31 30 30 53)"
			::= { onuUpdateTimerEntry 5 }

		
		-- 1.3.6.1.4.1.34592.1.3.100.12.4.1.1.6
		onuUpdateTimerPortList OBJECT-TYPE
			SYNTAX OCTET STRING
			MAX-ACCESS read-write
			STATUS current
			DESCRIPTION
				"PON端口列表(SIZE:8)，存储64位二进制，对应表示PON1-PON64。第n位置为1，表示升级第（n+1）个PON口下的ONU.
				采用类似INTERNET比特顺序，从左到右的OCTET分别为OCTET 0, OCTET 1, ...
				每个OCTET的bit从左到右分别为bit0, bit1, ..., bit7                
				第一个bit对应PON1，最后一个bit对应PON64
				例如：0x48 00 00 00 00 00 00 00 升级PON2和PON5下的ONU
				"
			::= { onuUpdateTimerEntry 6 }

		
		-- 1.3.6.1.4.1.34592.1.3.100.12.4.1.1.7
		onuUpdateTimerOntList OBJECT-TYPE
			SYNTAX OCTET STRING
			MAX-ACCESS read-write
			STATUS current
			DESCRIPTION
				"ONU配置列表(LONGEST SIZE:512)，采用类似INTERNET比特顺序，从左到右的OCTET分别为OCTET 0, OCTET 1, ....
				每个OCTET的bit从左到右分别为bit0, bit1, ..., bit7，第n位置为1，表示升级ONU（n+1）
				OCTET(0-7)的bit对应配置PON1下的ONU(1-64)
				OCTET(8-15)的bit对应配置PON2下的ONU(1-64)，依次类推
				例如：0x00 00 00 00 00 00 00 00 ff ff 00 00 00 00 00 00 升级PON2下的ONU(1-16) 				
				"
			::= { onuUpdateTimerEntry 7 }

		
		-- 1.3.6.1.4.1.34592.1.3.100.12.4.1.1.8
		onuUpdateTimerSystemTime OBJECT-TYPE
			SYNTAX DateAndTime
			MAX-ACCESS read-only
			STATUS current
			DESCRIPTION
				"Description."
			::= { onuUpdateTimerEntry 8 }

		
		-- 1.3.6.1.4.1.34592.1.3.100.12.4.1.1.9
		onuUpdateTimerConfigTime OBJECT-TYPE
			SYNTAX DateAndTime
			MAX-ACCESS read-write
			STATUS current
			DESCRIPTION
				"配置定时升级ONU的时间."
			::= { onuUpdateTimerEntry 9 }

		
		-- 1.3.6.1.4.1.34592.1.3.100.12.4.1.1.10
		onuUpdateTimerGlobalStatus OBJECT-TYPE
			SYNTAX DisplayString
			MAX-ACCESS read-only
			STATUS current
			DESCRIPTION
				"Description."
			::= { onuUpdateTimerEntry 10 }

		
		-- 1.3.6.1.4.1.34592.1.3.100.12.4.1.1.11
		onuUpdateTimerTotalNum OBJECT-TYPE
			SYNTAX Unsigned32
			MAX-ACCESS read-only
			STATUS current
			DESCRIPTION
				"Description."
			::= { onuUpdateTimerEntry 11 }

		
		-- 1.3.6.1.4.1.34592.1.3.100.12.4.1.1.12
		onuUpdateTimerSuccessNum OBJECT-TYPE
			SYNTAX Unsigned32
			MAX-ACCESS read-only
			STATUS current
			DESCRIPTION
				"Description."
			::= { onuUpdateTimerEntry 12 }

		
		-- 1.3.6.1.4.1.34592.1.3.100.12.4.1.1.13
		onuUpdateTimerFailureNum OBJECT-TYPE
			SYNTAX Unsigned32
			MAX-ACCESS read-only
			STATUS current
			DESCRIPTION
				"Description."
			::= { onuUpdateTimerEntry 13 }

		
		-- 1.3.6.1.4.1.34592.1.3.100.12.4.1.1.14
		onuUpdateTimerOntStatus OBJECT-TYPE
			SYNTAX OCTET STRING
			MAX-ACCESS read-only
			STATUS current
			DESCRIPTION
				"ONU升级状态列表(LONGEST SIZE:1024)，采用类似INTERNET比特顺序，从左到右的OCTET分别为OCTET 0, OCTET 1, ....
				每个OCTET的bit从左到右分别为bit0, bit1, ..., bit7，每2个bit可表示一个ONU的升级状态
				OCTET(0-15)的bit对应表示PON1下ONU(1-64)的升级状态
				OCTET(16-31)的bit对应表示PON2下ONU(1-64)的升级状态，依次类推
				4个值表示ONU的4种升级状态：
				0： no upgrade or wait for upgrade
				1： in upgrading
				2： success 
				3： failure 
				例如：
				PON2口的ONU3正在升级：
				0x00 00 00 00 00 00 00 00 00 00 00 00 00 00 00 00 04 00 00 00 00 00 00 00 00 00 00 00 00 00 00 00				
				PON2口的ONU3升级成功：
				0x00 00 00 00 00 00 00 00 00 00 00 00 00 00 00 00 08 00 00 00 00 00 00 00 00 00 00 00 00 00 00 00
				"
			::= { onuUpdateTimerEntry 14 }

		
		-- 1.3.6.1.4.1.34592.1.3.100.12.5
		onuCapabilityExtTable OBJECT-TYPE
			SYNTAX SEQUENCE OF OnuCapabilityExtEntry
			MAX-ACCESS not-accessible
			STATUS current
			DESCRIPTION
				"Description."
			::= { onuObjects 5 }

		
		-- 1.3.6.1.4.1.34592.1.3.100.12.5.1
		onuCapabilityExtEntry OBJECT-TYPE
			SYNTAX OnuCapabilityExtEntry
			MAX-ACCESS not-accessible
			STATUS current
			DESCRIPTION
				"Description."
			INDEX { onuCapabilityExtDeviceIndex }
			::= { onuCapabilityExtTable 1 }

		
		OnuCapabilityExtEntry ::=
			SEQUENCE { 
				onuCapabilityExtDeviceIndex
					NscrtvPonExtDeviceIndex,
				onuEthGePortNum
					Integer32,
				onuEthFePortNum
					Integer32,
				onuPotsPortNum
					Integer32,
				onuCatvPortNum
					Integer32,
				onuWifiPortNum
					Integer32,
				onuDevicesType
					Integer32,
				onuEncryptEnable
					INTEGER,
				onuMacLimit
					Integer32
			 }

		-- 1.3.6.1.4.1.34592.1.3.100.12.5.1.1
		onuCapabilityExtDeviceIndex OBJECT-TYPE
			SYNTAX NscrtvPonExtDeviceIndex
			MAX-ACCESS not-accessible
			STATUS current
			DESCRIPTION
				"Description."
			::= { onuCapabilityExtEntry 1 }

		
		-- 1.3.6.1.4.1.34592.1.3.100.12.5.1.2
		onuEthGePortNum OBJECT-TYPE
			SYNTAX Integer32
			MAX-ACCESS read-only
			STATUS current
			DESCRIPTION
				"Description."
			::= { onuCapabilityExtEntry 2 }

		
		-- 1.3.6.1.4.1.34592.1.3.100.12.5.1.3
		onuEthFePortNum OBJECT-TYPE
			SYNTAX Integer32
			MAX-ACCESS read-only
			STATUS current
			DESCRIPTION
				"Description."
			::= { onuCapabilityExtEntry 3 }

		
		-- 1.3.6.1.4.1.34592.1.3.100.12.5.1.4
		onuPotsPortNum OBJECT-TYPE
			SYNTAX Integer32
			MAX-ACCESS read-only
			STATUS current
			DESCRIPTION
				"Description."
			::= { onuCapabilityExtEntry 4 }

		
		-- 1.3.6.1.4.1.34592.1.3.100.12.5.1.5
		onuCatvPortNum OBJECT-TYPE
			SYNTAX Integer32
			MAX-ACCESS read-only
			STATUS current
			DESCRIPTION
				"Description."
			::= { onuCapabilityExtEntry 5 }

		
		-- 1.3.6.1.4.1.34592.1.3.100.12.5.1.6
		onuWifiPortNum OBJECT-TYPE
			SYNTAX Integer32
			MAX-ACCESS read-only
			STATUS current
			DESCRIPTION
				"Description."
			::= { onuCapabilityExtEntry 6 }

		
		-- 1.3.6.1.4.1.34592.1.3.100.12.5.1.7
		onuDevicesType OBJECT-TYPE
			SYNTAX Integer32
			MAX-ACCESS read-only
			STATUS current
			DESCRIPTION
				"Description."
			::= { onuCapabilityExtEntry 7 }

		
		-- 1.3.6.1.4.1.34592.1.3.100.12.5.1.8
		onuEncryptEnable OBJECT-TYPE
			SYNTAX INTEGER
				{
				disable(0),
				enable(1)
				}
			MAX-ACCESS read-write
			STATUS current
			DESCRIPTION
				"Description."
			::= { onuCapabilityExtEntry 8 }

		
		-- 1.3.6.1.4.1.34592.1.3.100.12.5.1.9
		onuMacLimit OBJECT-TYPE
			SYNTAX Integer32 (0..16384)
			MAX-ACCESS read-write
			STATUS current
			DESCRIPTION
				"Description."
			::= { onuCapabilityExtEntry 9 }

		
		-- 1.3.6.1.4.1.34592.1.3.100.12.6
		onuInfoCollectionTable OBJECT-TYPE
			SYNTAX SEQUENCE OF OnuInfoCollectionEntry
			MAX-ACCESS not-accessible
			STATUS current
			DESCRIPTION
				"Description."
			::= { onuObjects 6 }

		
		-- 1.3.6.1.4.1.34592.1.3.100.12.6.1
		onuInfoCollectionEntry OBJECT-TYPE
			SYNTAX OnuInfoCollectionEntry
			MAX-ACCESS not-accessible
			STATUS current
			DESCRIPTION
				"Description."
			INDEX { onuInfoCollectionIndex }
			::= { onuInfoCollectionTable 1 }

		
		OnuInfoCollectionEntry ::=
			SEQUENCE { 
				onuInfoCollectionIndex
					Integer32,
				onuInfoCollectionData
					DisplayString
			 }

		-- 1.3.6.1.4.1.34592.1.3.100.12.6.1.1
		onuInfoCollectionIndex OBJECT-TYPE
			SYNTAX Integer32
			MAX-ACCESS not-accessible
			STATUS current
			DESCRIPTION
				"Description."
			::= { onuInfoCollectionEntry 1 }

		
		-- 1.3.6.1.4.1.34592.1.3.100.12.6.1.2
		onuInfoCollectionData OBJECT-TYPE
			SYNTAX DisplayString
			MAX-ACCESS read-only
			STATUS current
			DESCRIPTION
				"Description."
			::= { onuInfoCollectionEntry 2 }

		
		-- 1.3.6.1.4.1.34592.1.3.100.12.7
		onuCurStatsTable OBJECT-TYPE
			SYNTAX SEQUENCE OF OnuCurStatsEntry
			MAX-ACCESS not-accessible
			STATUS current
			DESCRIPTION
				"Description."
			::= { onuObjects 7 }

		
		-- 1.3.6.1.4.1.34592.1.3.100.12.7.1
		onuCurStatsEntry OBJECT-TYPE
			SYNTAX OnuCurStatsEntry
			MAX-ACCESS not-accessible
			STATUS current
			DESCRIPTION
				"Description."
			INDEX { onuCurStatsDeviceIndex }
			::= { onuCurStatsTable 1 }

		
		OnuCurStatsEntry ::=
			SEQUENCE { 
				onuCurStatsDeviceIndex
					NscrtvPonExtDeviceIndex,
				onuCurStatsOutPkts
					Counter64,
				onuCurStatsInPkts
					Counter64,
				onuCurStatsOutBytes
					Counter64,
				onuCurStatsInBytes
					Counter64
			 }

		-- 1.3.6.1.4.1.34592.1.3.100.12.7.1.1
		onuCurStatsDeviceIndex OBJECT-TYPE
			SYNTAX NscrtvPonExtDeviceIndex
			MAX-ACCESS read-only
			STATUS current
			DESCRIPTION
				"Description."
			::= { onuCurStatsEntry 1 }

		
		-- 1.3.6.1.4.1.34592.1.3.100.12.7.1.2
		onuCurStatsOutPkts OBJECT-TYPE
			SYNTAX Counter64
			MAX-ACCESS read-only
			STATUS current
			DESCRIPTION
				"Description."
			::= { onuCurStatsEntry 2 }

		
		-- 1.3.6.1.4.1.34592.1.3.100.12.7.1.3
		onuCurStatsInPkts OBJECT-TYPE
			SYNTAX Counter64
			MAX-ACCESS read-only
			STATUS current
			DESCRIPTION
				"Description."
			::= { onuCurStatsEntry 3 }

		
		-- 1.3.6.1.4.1.34592.1.3.100.12.7.1.4
		onuCurStatsOutBytes OBJECT-TYPE
			SYNTAX Counter64
			MAX-ACCESS read-only
			STATUS current
			DESCRIPTION
				"Description."
			::= { onuCurStatsEntry 4 }

		
		-- 1.3.6.1.4.1.34592.1.3.100.12.7.1.5
		onuCurStatsInBytes OBJECT-TYPE
			SYNTAX Counter64
			MAX-ACCESS read-only
			STATUS current
			DESCRIPTION
				"Description."
			::= { onuCurStatsEntry 5 }

		
		-- 1.3.6.1.4.1.34592.1.3.100.13
		uniObjects OBJECT IDENTIFIER ::= { nscrtvPonTreeExt 13 }

		
		-- 1.3.6.1.4.1.34592.1.3.100.13.1
		uniLearnedMacAddrTable OBJECT-TYPE
			SYNTAX SEQUENCE OF UniLearnedMacAddrEntry
			MAX-ACCESS not-accessible
			STATUS current
			DESCRIPTION
				"Description."
			::= { uniObjects 1 }

		
		-- 1.3.6.1.4.1.34592.1.3.100.13.1.1
		uniLearnedMacAddrEntry OBJECT-TYPE
			SYNTAX UniLearnedMacAddrEntry
			MAX-ACCESS not-accessible
			STATUS current
			DESCRIPTION
				"Description."
			INDEX { uniLearnedMacAddrDeviceIndex, uniLearnedMacAddrCardIndex, uniLearnedMacAddrPortIndex, uniLearnedMacAddrIndex }
			::= { uniLearnedMacAddrTable 1 }

		
		UniLearnedMacAddrEntry ::=
			SEQUENCE { 
				uniLearnedMacAddrDeviceIndex
					NscrtvPonExtDeviceIndex,
				uniLearnedMacAddrCardIndex
					NscrtvPonExtCardIndex,
				uniLearnedMacAddrPortIndex
					NscrtvPonPortIndex,
				uniLearnedMacAddrIndex
					Integer32,
				uniLearnedMacAddr
					MacAddress
			 }

		-- 1.3.6.1.4.1.34592.1.3.100.13.1.1.1
		uniLearnedMacAddrDeviceIndex OBJECT-TYPE
			SYNTAX NscrtvPonExtDeviceIndex
			MAX-ACCESS not-accessible
			STATUS current
			DESCRIPTION
				"Description."
			::= { uniLearnedMacAddrEntry 1 }

		
		-- 1.3.6.1.4.1.34592.1.3.100.13.1.1.2
		uniLearnedMacAddrCardIndex OBJECT-TYPE
			SYNTAX NscrtvPonExtCardIndex
			MAX-ACCESS not-accessible
			STATUS current
			DESCRIPTION
				"Description."
			::= { uniLearnedMacAddrEntry 2 }

		
		-- 1.3.6.1.4.1.34592.1.3.100.13.1.1.3
		uniLearnedMacAddrPortIndex OBJECT-TYPE
			SYNTAX NscrtvPonPortIndex
			MAX-ACCESS not-accessible
			STATUS current
			DESCRIPTION
				"Description."
			::= { uniLearnedMacAddrEntry 3 }

		
		-- 1.3.6.1.4.1.34592.1.3.100.13.1.1.4
		uniLearnedMacAddrIndex OBJECT-TYPE
			SYNTAX Integer32
			MAX-ACCESS not-accessible
			STATUS current
			DESCRIPTION
				"Description."
			::= { uniLearnedMacAddrEntry 4 }

		
		-- 1.3.6.1.4.1.34592.1.3.100.13.1.1.5
		uniLearnedMacAddr OBJECT-TYPE
			SYNTAX MacAddress
			MAX-ACCESS read-only
			STATUS current
			DESCRIPTION
				"Description."
			::= { uniLearnedMacAddrEntry 5 }

		
		-- 1.3.6.1.4.1.34592.1.3.100.14
		aclManagementObjects OBJECT IDENTIFIER ::= { nscrtvPonTreeExt 14 }

		
		-- 1.3.6.1.4.1.34592.1.3.100.14.1
		timeRangeTable OBJECT-TYPE
			SYNTAX SEQUENCE OF TimeRangeEntry
			MAX-ACCESS not-accessible
			STATUS current
			DESCRIPTION
				"Description."
			::= { aclManagementObjects 1 }

		
		-- 1.3.6.1.4.1.34592.1.3.100.14.1.1
		timeRangeEntry OBJECT-TYPE
			SYNTAX TimeRangeEntry
			MAX-ACCESS not-accessible
			STATUS current
			DESCRIPTION
				"Description."
			INDEX { timeRangeIndex }
			::= { timeRangeTable 1 }

		
		TimeRangeEntry ::=
			SEQUENCE { 
				timeRangeIndex
					INTEGER,
				timeRangeName
					DisplayString,
				timeRangeType
					INTEGER,
				timeRangeState
					DisplayString,
				relativeTimeStart
					DisplayString,
				relativeTimeEnd
					DisplayString,
				relativeTimeCycle
					INTEGER,
				absoluteTimeStart
					DisplayString,
				absoluteTimeEnd
					DisplayString,
				timeRangeRowStatus
					RowStatus
			 }

		-- 1.3.6.1.4.1.34592.1.3.100.14.1.1.1
		timeRangeIndex OBJECT-TYPE
			SYNTAX INTEGER (1..256)
			MAX-ACCESS not-accessible
			STATUS current
			DESCRIPTION
				"Index: 1-256"
			::= { timeRangeEntry 1 }

		
		-- 1.3.6.1.4.1.34592.1.3.100.14.1.1.2
		timeRangeName OBJECT-TYPE
			SYNTAX DisplayString (SIZE (1..10))
			MAX-ACCESS read-create
			STATUS current
			DESCRIPTION
				"LONGEST SIZE: 10"
			::= { timeRangeEntry 2 }

		
		-- 1.3.6.1.4.1.34592.1.3.100.14.1.1.3
		timeRangeType OBJECT-TYPE
			SYNTAX INTEGER
				{
				absoluteTime(1),
				relativeTime(2)
				}
			MAX-ACCESS read-create
			STATUS current
			DESCRIPTION
				"Description."
			::= { timeRangeEntry 3 }

		
		-- 1.3.6.1.4.1.34592.1.3.100.14.1.1.4
		timeRangeState OBJECT-TYPE
			SYNTAX DisplayString
			MAX-ACCESS read-only
			STATUS current
			DESCRIPTION
				"Description."
			::= { timeRangeEntry 4 }

		
		-- 1.3.6.1.4.1.34592.1.3.100.14.1.1.5
		relativeTimeStart OBJECT-TYPE
			SYNTAX DisplayString (SIZE (5))
			MAX-ACCESS read-create
			STATUS current
			DESCRIPTION
				"Format: HH:MM
				For exmaple: 08:01"
			::= { timeRangeEntry 5 }

		
		-- 1.3.6.1.4.1.34592.1.3.100.14.1.1.6
		relativeTimeEnd OBJECT-TYPE
			SYNTAX DisplayString (SIZE (5))
			MAX-ACCESS read-create
			STATUS current
			DESCRIPTION
				"Format: HH:MM
				For exmaple: 23:10"
			::= { timeRangeEntry 6 }

		
		-- 1.3.6.1.4.1.34592.1.3.100.14.1.1.7
		relativeTimeCycle OBJECT-TYPE
			SYNTAX INTEGER
				{
				Sunday(1),
				Monday(2),
				Tuesday(3),
				Wednesday(4),
				Thurday(5),
				Friday(6),
				Saturday(7),
				Daily(8),
				Weekend(9),
				WorkingDay(10)
				}
			MAX-ACCESS read-create
			STATUS current
			DESCRIPTION
				"Description."
			::= { timeRangeEntry 7 }

		
		-- 1.3.6.1.4.1.34592.1.3.100.14.1.1.8
		absoluteTimeStart OBJECT-TYPE
			SYNTAX DisplayString (SIZE (16))
			MAX-ACCESS read-create
			STATUS current
			DESCRIPTION
				"Format: YYYY/MM/DD HH:MM
				For exmaple: 2019/01/02 08:01"
			::= { timeRangeEntry 8 }

		
		-- 1.3.6.1.4.1.34592.1.3.100.14.1.1.9
		absoluteTimeEnd OBJECT-TYPE
			SYNTAX DisplayString (SIZE (16))
			MAX-ACCESS read-create
			STATUS current
			DESCRIPTION
				"Format: YYYY/MM/DD HH:MM
				For exmaple: 2019/10/28 23:10"
			::= { timeRangeEntry 9 }

		
		-- 1.3.6.1.4.1.34592.1.3.100.14.1.1.10
		timeRangeRowStatus OBJECT-TYPE
			SYNTAX RowStatus
			MAX-ACCESS read-create
			STATUS current
			DESCRIPTION
				"Description."
			::= { timeRangeEntry 10 }

		
		-- 1.3.6.1.4.1.34592.1.3.100.14.2
		bindConfigTable OBJECT-TYPE
			SYNTAX SEQUENCE OF BindConfigEntry
			MAX-ACCESS not-accessible
			STATUS current
			DESCRIPTION
				"Description."
			::= { aclManagementObjects 2 }

		
		-- 1.3.6.1.4.1.34592.1.3.100.14.2.1
		bindConfigEntry OBJECT-TYPE
			SYNTAX BindConfigEntry
			MAX-ACCESS not-accessible
			STATUS current
			DESCRIPTION
				"Description."
			INDEX { bindConfigAclId, bindConfigRuleId }
			::= { bindConfigTable 1 }

		
		BindConfigEntry ::=
			SEQUENCE { 
				bindConfigAclId
					INTEGER,
				bindConfigRuleId
					INTEGER,
				bindConfigName
					DisplayString,
				bindConfigRowStatus
					RowStatus
			 }

		-- 1.3.6.1.4.1.34592.1.3.100.14.2.1.1
		bindConfigAclId OBJECT-TYPE
			SYNTAX INTEGER
			MAX-ACCESS not-accessible
			STATUS current
			DESCRIPTION
				"Description."
			::= { bindConfigEntry 1 }

		
		-- 1.3.6.1.4.1.34592.1.3.100.14.2.1.2
		bindConfigRuleId OBJECT-TYPE
			SYNTAX INTEGER
			MAX-ACCESS not-accessible
			STATUS current
			DESCRIPTION
				"Description."
			::= { bindConfigEntry 2 }

		
		-- 1.3.6.1.4.1.34592.1.3.100.14.2.1.3
		bindConfigName OBJECT-TYPE
			SYNTAX DisplayString (SIZE (1..10))
			MAX-ACCESS read-create
			STATUS current
			DESCRIPTION
				"LONGEST SIZE: 10"
			::= { bindConfigEntry 3 }

		
		-- 1.3.6.1.4.1.34592.1.3.100.14.2.1.4
		bindConfigRowStatus OBJECT-TYPE
			SYNTAX RowStatus
			MAX-ACCESS read-create
			STATUS current
			DESCRIPTION
				"Description."
			::= { bindConfigEntry 4 }

		
		-- 1.3.6.1.4.1.34592.1.3.100.14.3
		aclMixRuleTable OBJECT-TYPE
			SYNTAX SEQUENCE OF AclMixRuleEntry
			MAX-ACCESS not-accessible
			STATUS current
			DESCRIPTION
				"Description."
			::= { aclManagementObjects 3 }

		
		-- 1.3.6.1.4.1.34592.1.3.100.14.3.1
		aclMixRuleEntry OBJECT-TYPE
			SYNTAX AclMixRuleEntry
			MAX-ACCESS not-accessible
			STATUS current
			DESCRIPTION
				"Description."
			INDEX { aclMixRuleListIndex, aclMixRuleIndex }
			::= { aclMixRuleTable 1 }

		
		AclMixRuleEntry ::=
			SEQUENCE { 
				aclMixRuleListIndex
					INTEGER,
				aclMixRuleIndex
					INTEGER,
				matchedMixRuleSourceMac
					MacAddress,
				matchedMixRuleDestinationMac
					MacAddress,
				matchedMixRuleEthernetType
					INTEGER,
				matchedMixRuleVlanId
					INTEGER,
				matchedMixRuleCos
					INTEGER,
				matchedMixRuleSourceIP
					IpAddress,
				matchedMixRuleDestinationIP
					IpAddress,
				matchedMixRuleProtocol
					INTEGER,
				matchedMixRuleDscp
					INTEGER,
				matchedMixRuleSourcePort
					INTEGER,
				matchedMixRuleDestinationPort
					INTEGER,
				aclMixRuleAction
					INTEGER,
				aclMixRuleActionParameter
					OCTET STRING,
				matchedMixRuleSourceMacMask
					MacAddress,
				matchedMixRuleDestinationMacMask
					MacAddress,
				matchedMixRuleSourceIPMask
					IpAddress,
				matchedMixRuleDestinationIPMask
					IpAddress,
				aclMixRuleRowStatus
					RowStatus
			 }

		-- 1.3.6.1.4.1.34592.1.3.100.14.3.1.1
		aclMixRuleListIndex OBJECT-TYPE
			SYNTAX INTEGER
			MAX-ACCESS not-accessible
			STATUS current
			DESCRIPTION
				"
				Rule表acl list索引(基于acl列表已创建的list index)"
			::= { aclMixRuleEntry 1 }

		
		-- 1.3.6.1.4.1.34592.1.3.100.14.3.1.2
		aclMixRuleIndex OBJECT-TYPE
			SYNTAX INTEGER
			MAX-ACCESS not-accessible
			STATUS current
			DESCRIPTION
				"
				ACL规则索引"
			::= { aclMixRuleEntry 2 }

		
		-- 1.3.6.1.4.1.34592.1.3.100.14.3.1.3
		matchedMixRuleSourceMac OBJECT-TYPE
			SYNTAX MacAddress
			MAX-ACCESS read-create
			STATUS current
			DESCRIPTION
				"
				匹配的源Mac"
			::= { aclMixRuleEntry 3 }

		
		-- 1.3.6.1.4.1.34592.1.3.100.14.3.1.4
		matchedMixRuleDestinationMac OBJECT-TYPE
			SYNTAX MacAddress
			MAX-ACCESS read-create
			STATUS current
			DESCRIPTION
				"
				匹配的目的Mac"
			::= { aclMixRuleEntry 4 }

		
		-- 1.3.6.1.4.1.34592.1.3.100.14.3.1.5
		matchedMixRuleEthernetType OBJECT-TYPE
			SYNTAX INTEGER
			MAX-ACCESS read-create
			STATUS current
			DESCRIPTION
				"
				匹配的以太网类型
				It is presented in decimal value for heximal EtherType
				比如ARP(0x0806),十进制值为2054
				"
			::= { aclMixRuleEntry 5 }

		
		-- 1.3.6.1.4.1.34592.1.3.100.14.3.1.6
		matchedMixRuleVlanId OBJECT-TYPE
			SYNTAX INTEGER
			MAX-ACCESS read-create
			STATUS current
			DESCRIPTION
				"
				匹配的vlan id"
			::= { aclMixRuleEntry 6 }

		
		-- 1.3.6.1.4.1.34592.1.3.100.14.3.1.7
		matchedMixRuleCos OBJECT-TYPE
			SYNTAX INTEGER
			MAX-ACCESS read-create
			STATUS current
			DESCRIPTION
				"
				匹配的cos"
			::= { aclMixRuleEntry 7 }

		
		-- 1.3.6.1.4.1.34592.1.3.100.14.3.1.8
		matchedMixRuleSourceIP OBJECT-TYPE
			SYNTAX IpAddress
			MAX-ACCESS read-create
			STATUS current
			DESCRIPTION
				"
				匹配的源IP"
			::= { aclMixRuleEntry 8 }

		
		-- 1.3.6.1.4.1.34592.1.3.100.14.3.1.9
		matchedMixRuleDestinationIP OBJECT-TYPE
			SYNTAX IpAddress
			MAX-ACCESS read-create
			STATUS current
			DESCRIPTION
				"
				匹配的目的IP"
			::= { aclMixRuleEntry 9 }

		
		-- 1.3.6.1.4.1.34592.1.3.100.14.3.1.10
		matchedMixRuleProtocol OBJECT-TYPE
			SYNTAX INTEGER (0..255)
			MAX-ACCESS read-create
			STATUS current
			DESCRIPTION
				"
				匹配的报文协议类型"
			::= { aclMixRuleEntry 10 }

		
		-- 1.3.6.1.4.1.34592.1.3.100.14.3.1.11
		matchedMixRuleDscp OBJECT-TYPE
			SYNTAX INTEGER (0..63)
			MAX-ACCESS read-create
			STATUS current
			DESCRIPTION
				"
				匹配的dscp"
			::= { aclMixRuleEntry 11 }

		
		-- 1.3.6.1.4.1.34592.1.3.100.14.3.1.12
		matchedMixRuleSourcePort OBJECT-TYPE
			SYNTAX INTEGER
			MAX-ACCESS read-create
			STATUS current
			DESCRIPTION
				"
				匹配的源端口"
			::= { aclMixRuleEntry 12 }

		
		-- 1.3.6.1.4.1.34592.1.3.100.14.3.1.13
		matchedMixRuleDestinationPort OBJECT-TYPE
			SYNTAX INTEGER
			MAX-ACCESS read-create
			STATUS current
			DESCRIPTION
				"
				匹配的目的端口"
			::= { aclMixRuleEntry 13 }

		
		-- 1.3.6.1.4.1.34592.1.3.100.14.3.1.14
		aclMixRuleAction OBJECT-TYPE
			SYNTAX INTEGER
				{
				permit(1),
				deny(2),
				mark(3)
				}
			MAX-ACCESS read-create
			STATUS current
			DESCRIPTION
				"
				ACL规则动作(permit、deny、标记等)"
			::= { aclMixRuleEntry 14 }

		
		-- 1.3.6.1.4.1.34592.1.3.100.14.3.1.15
		aclMixRuleActionParameter OBJECT-TYPE
			SYNTAX OCTET STRING
			MAX-ACCESS read-create
			STATUS current
			DESCRIPTION
				"
				ACL规则动作参数。只对aclAction为mark(3)有效,对于aclAction其他值,
				此对象禁止配置,get时返回NULL。        
				按照INTERNET顺序从左往右的方向排列,第一个为OCTET0,第n个为OCTET
				[n-1]。        
				OCTET 0 表示 MARK 类型。后面的OCTET 表示这种类型的MARK的目标值,这
				是否这些OCTET的长度取决于MARK类型,比如对应于改MARK类型的参数的SYNTAX
				为INTEGER,则需要4个字节,表示对应的数值。        
				MARK类型    目标值的SYNTAX        描述
				-------------------------------------------------------------------
				0                             Reserved
				1       INTEGER (0..7)      MARK 801.1p的值(外层VLAN)
				2       INTEGER (1..4094)   MARK VLAN ID(外层VLAN)
				3       INTEGER (0..7)      MARK TOS PRECEDENCE
				4       INTEGER (0..63)     MARK DSCP
				5..255                            Reserved        
				比如修改VLAN ID为100,对应的值为：02 00 00 00 64"
			::= { aclMixRuleEntry 15 }

		
		-- 1.3.6.1.4.1.34592.1.3.100.14.3.1.16
		matchedMixRuleSourceMacMask OBJECT-TYPE
			SYNTAX MacAddress
			MAX-ACCESS read-create
			STATUS current
			DESCRIPTION
				"
				匹配的源Mac 反掩码.
				"
			::= { aclMixRuleEntry 16 }

		
		-- 1.3.6.1.4.1.34592.1.3.100.14.3.1.17
		matchedMixRuleDestinationMacMask OBJECT-TYPE
			SYNTAX MacAddress
			MAX-ACCESS read-create
			STATUS current
			DESCRIPTION
				"
				匹配的目的Mac反掩码.
				"
			::= { aclMixRuleEntry 17 }

		
		-- 1.3.6.1.4.1.34592.1.3.100.14.3.1.18
		matchedMixRuleSourceIPMask OBJECT-TYPE
			SYNTAX IpAddress
			MAX-ACCESS read-create
			STATUS current
			DESCRIPTION
				"
				匹配的源IP反掩码.
				"
			::= { aclMixRuleEntry 18 }

		
		-- 1.3.6.1.4.1.34592.1.3.100.14.3.1.19
		matchedMixRuleDestinationIPMask OBJECT-TYPE
			SYNTAX IpAddress
			MAX-ACCESS read-create
			STATUS current
			DESCRIPTION
				"
				匹配的目的IP反掩码.
				"
			::= { aclMixRuleEntry 19 }

		
		-- 1.3.6.1.4.1.34592.1.3.100.14.3.1.20
		aclMixRuleRowStatus OBJECT-TYPE
			SYNTAX RowStatus
			MAX-ACCESS read-create
			STATUS current
			DESCRIPTION
				"
				规则状态"
			::= { aclMixRuleEntry 20 }

		
		-- 1.3.6.1.4.1.34592.1.3.100.14.4
		portACLListExtTable OBJECT-TYPE
			SYNTAX SEQUENCE OF PortACLListExtEntry
			MAX-ACCESS not-accessible
			STATUS current
			DESCRIPTION
				"Description."
			::= { aclManagementObjects 4 }

		
		-- 1.3.6.1.4.1.34592.1.3.100.14.4.1
		portACLListExtEntry OBJECT-TYPE
			SYNTAX PortACLListExtEntry
			MAX-ACCESS not-accessible
			STATUS current
			DESCRIPTION
				"Description."
			INDEX { portAclDeviceIndex, portAclListExtIndex, portAclListExtRule }
			::= { portACLListExtTable 1 }

		
		PortACLListExtEntry ::=
			SEQUENCE { 
				portAclDeviceIndex
					EponDeviceIndex,
				portAclListExtIndex
					INTEGER,
				portAclListExtRule
					INTEGER,
				portAclListExtDirection
					OCTET STRING,
				portAclListExtRowStatus
					RowStatus,
				portAclListExtParameter
					OCTET STRING,
				portAclListExtTimeRange
					DisplayString
			 }

		-- 1.3.6.1.4.1.34592.1.3.100.14.4.1.1
		portAclDeviceIndex OBJECT-TYPE
			SYNTAX EponDeviceIndex
			MAX-ACCESS not-accessible
			STATUS current
			DESCRIPTION
				"Description."
			::= { portACLListExtEntry 1 }

		
		-- 1.3.6.1.4.1.34592.1.3.100.14.4.1.2
		portAclListExtIndex OBJECT-TYPE
			SYNTAX INTEGER
			MAX-ACCESS not-accessible
			STATUS current
			DESCRIPTION
				"Description."
			::= { portACLListExtEntry 2 }

		
		-- 1.3.6.1.4.1.34592.1.3.100.14.4.1.3
		portAclListExtRule OBJECT-TYPE
			SYNTAX INTEGER
			MAX-ACCESS not-accessible
			STATUS current
			DESCRIPTION
				"Description."
			::= { portACLListExtEntry 3 }

		
		-- 1.3.6.1.4.1.34592.1.3.100.14.4.1.4
		portAclListExtDirection OBJECT-TYPE
			SYNTAX OCTET STRING
			MAX-ACCESS read-create
			STATUS current
			DESCRIPTION
				"Description."
			::= { portACLListExtEntry 4 }

		
		-- 1.3.6.1.4.1.34592.1.3.100.14.4.1.5
		portAclListExtRowStatus OBJECT-TYPE
			SYNTAX RowStatus
			MAX-ACCESS read-create
			STATUS current
			DESCRIPTION
				"Description."
			::= { portACLListExtEntry 5 }

		
		-- 1.3.6.1.4.1.34592.1.3.100.14.4.1.6
		portAclListExtParameter OBJECT-TYPE
			SYNTAX OCTET STRING
			MAX-ACCESS read-create
			STATUS current
			DESCRIPTION
				"Description."
			::= { portACLListExtEntry 6 }

		
		-- 1.3.6.1.4.1.34592.1.3.100.14.4.1.7
		portAclListExtTimeRange OBJECT-TYPE
			SYNTAX DisplayString (SIZE (1..10))
			MAX-ACCESS read-create
			STATUS current
			DESCRIPTION
				"Description."
			::= { portACLListExtEntry 7 }

		
		-- 1.3.6.1.4.1.34592.1.3.100.15
		macFlappingDetectionManagementObjects OBJECT IDENTIFIER ::= { nscrtvPonTreeExt 15 }

		
		-- 1.3.6.1.4.1.34592.1.3.100.15.1
		macFlappingDetectionGlobalSetTable OBJECT-TYPE
			SYNTAX SEQUENCE OF MacFlappingDetectionGlobalSetEntry
			MAX-ACCESS not-accessible
			STATUS current
			DESCRIPTION
				"Description."
			::= { macFlappingDetectionManagementObjects 1 }

		
		-- 1.3.6.1.4.1.34592.1.3.100.15.1.1
		macFlappingDetectionGlobalSetEntry OBJECT-TYPE
			SYNTAX MacFlappingDetectionGlobalSetEntry
			MAX-ACCESS not-accessible
			STATUS current
			DESCRIPTION
				"Description."
			INDEX { macFlappingDetectionGloabDeviceIndex }
			::= { macFlappingDetectionGlobalSetTable 1 }

		
		MacFlappingDetectionGlobalSetEntry ::=
			SEQUENCE { 
				macFlappingDetectionGloabDeviceIndex
					NscrtvPonExtDeviceIndex,
				macFlappingDetectionGlobalEnable
					TruthValue,
				macFlappingDetectionGlobalPeriodTime
					Unsigned32,
				macFlappingDetectionGlobalAgingTime
					Unsigned32,
				macFlappingDetectionGlobalThreshold
					Unsigned32,
				macFlappingDetectionGlobalRecordClear
					INTEGER
			 }

		-- 1.3.6.1.4.1.34592.1.3.100.15.1.1.1
		macFlappingDetectionGloabDeviceIndex OBJECT-TYPE
			SYNTAX NscrtvPonExtDeviceIndex
			MAX-ACCESS not-accessible
			STATUS current
			DESCRIPTION
				"Description."
			::= { macFlappingDetectionGlobalSetEntry 1 }

		
		-- 1.3.6.1.4.1.34592.1.3.100.15.1.1.2
		macFlappingDetectionGlobalEnable OBJECT-TYPE
			SYNTAX TruthValue
			MAX-ACCESS read-write
			STATUS current
			DESCRIPTION
				"Description."
			::= { macFlappingDetectionGlobalSetEntry 2 }

		
		-- 1.3.6.1.4.1.34592.1.3.100.15.1.1.3
		macFlappingDetectionGlobalPeriodTime OBJECT-TYPE
			SYNTAX Unsigned32 (10..300)
			MAX-ACCESS read-write
			STATUS current
			DESCRIPTION
				"Description."
			::= { macFlappingDetectionGlobalSetEntry 3 }

		
		-- 1.3.6.1.4.1.34592.1.3.100.15.1.1.4
		macFlappingDetectionGlobalAgingTime OBJECT-TYPE
			SYNTAX Unsigned32 (60..900)
			MAX-ACCESS read-write
			STATUS current
			DESCRIPTION
				"Description."
			::= { macFlappingDetectionGlobalSetEntry 4 }

		
		-- 1.3.6.1.4.1.34592.1.3.100.15.1.1.5
		macFlappingDetectionGlobalThreshold OBJECT-TYPE
			SYNTAX Unsigned32 (3..100)
			MAX-ACCESS read-write
			STATUS current
			DESCRIPTION
				"Description."
			::= { macFlappingDetectionGlobalSetEntry 5 }

		
		-- 1.3.6.1.4.1.34592.1.3.100.15.1.1.6
		macFlappingDetectionGlobalRecordClear OBJECT-TYPE
			SYNTAX INTEGER
				{
				none(0),
				all(1)
				}
			MAX-ACCESS read-write
			STATUS current
			DESCRIPTION
				"Description."
			::= { macFlappingDetectionGlobalSetEntry 6 }

		
		-- 1.3.6.1.4.1.34592.1.3.100.15.2
		macFlappingDetectionPortConfigTable OBJECT-TYPE
			SYNTAX SEQUENCE OF MacFlappingDetectionPortConfigEntry
			MAX-ACCESS not-accessible
			STATUS current
			DESCRIPTION
				"Description."
			::= { macFlappingDetectionManagementObjects 2 }

		
		-- 1.3.6.1.4.1.34592.1.3.100.15.2.1
		macFlappingDetectionPortConfigEntry OBJECT-TYPE
			SYNTAX MacFlappingDetectionPortConfigEntry
			MAX-ACCESS not-accessible
			STATUS current
			DESCRIPTION
				"Description."
			INDEX { macFlappingDetectionPortConfigDeviceIndex, macFlappingDetectionPortConfigCardIndex, macFlappingDetectionPortConfigPortIndex }
			::= { macFlappingDetectionPortConfigTable 1 }

		
		MacFlappingDetectionPortConfigEntry ::=
			SEQUENCE { 
				macFlappingDetectionPortConfigDeviceIndex
					NscrtvPonExtDeviceIndex,
				macFlappingDetectionPortConfigCardIndex
					NscrtvPonExtCardIndex,
				macFlappingDetectionPortConfigPortIndex
					NscrtvPonPortIndex,
				macFlappingDetectionPortConfigEnable
					TruthValue,
				macFlappingDetectionPortConfigAction
					INTEGER,
				macFlappingortConfigAutoRecoverEnable
					TruthValue,
				macFlappingDetectionPortConfigAutoRecoverTime
					INTEGER,
				macFlappingDetectionPortStatus
					INTEGER,
				macFlappingDetectionPortLinkStatus
					INTEGER
			 }

		-- 1.3.6.1.4.1.34592.1.3.100.15.2.1.1
		macFlappingDetectionPortConfigDeviceIndex OBJECT-TYPE
			SYNTAX NscrtvPonExtDeviceIndex
			MAX-ACCESS not-accessible
			STATUS current
			DESCRIPTION
				"Description."
			::= { macFlappingDetectionPortConfigEntry 1 }

		
		-- 1.3.6.1.4.1.34592.1.3.100.15.2.1.2
		macFlappingDetectionPortConfigCardIndex OBJECT-TYPE
			SYNTAX NscrtvPonExtCardIndex
			MAX-ACCESS not-accessible
			STATUS current
			DESCRIPTION
				"Description."
			::= { macFlappingDetectionPortConfigEntry 2 }

		
		-- 1.3.6.1.4.1.34592.1.3.100.15.2.1.3
		macFlappingDetectionPortConfigPortIndex OBJECT-TYPE
			SYNTAX NscrtvPonPortIndex
			MAX-ACCESS not-accessible
			STATUS current
			DESCRIPTION
				"Description."
			::= { macFlappingDetectionPortConfigEntry 3 }

		
		-- 1.3.6.1.4.1.34592.1.3.100.15.2.1.4
		macFlappingDetectionPortConfigEnable OBJECT-TYPE
			SYNTAX TruthValue
			MAX-ACCESS read-write
			STATUS current
			DESCRIPTION
				"Description."
			::= { macFlappingDetectionPortConfigEntry 4 }

		
		-- 1.3.6.1.4.1.34592.1.3.100.15.2.1.5
		macFlappingDetectionPortConfigAction OBJECT-TYPE
			SYNTAX INTEGER
				{
				alarm-only(0),
				block(1),
				shutdown(2)
				}
			MAX-ACCESS read-write
			STATUS current
			DESCRIPTION
				"Description."
			::= { macFlappingDetectionPortConfigEntry 5 }

		
		-- 1.3.6.1.4.1.34592.1.3.100.15.2.1.6
		macFlappingortConfigAutoRecoverEnable OBJECT-TYPE
			SYNTAX TruthValue
			MAX-ACCESS read-write
			STATUS current
			DESCRIPTION
				"Description."
			::= { macFlappingDetectionPortConfigEntry 6 }

		
		-- 1.3.6.1.4.1.34592.1.3.100.15.2.1.7
		macFlappingDetectionPortConfigAutoRecoverTime OBJECT-TYPE
			SYNTAX INTEGER (20..1200)
			MAX-ACCESS read-write
			STATUS current
			DESCRIPTION
				"Description."
			::= { macFlappingDetectionPortConfigEntry 7 }

		
		-- 1.3.6.1.4.1.34592.1.3.100.15.2.1.8
		macFlappingDetectionPortStatus OBJECT-TYPE
			SYNTAX INTEGER
				{
				detected(1),
				undetected(2)
				}
			MAX-ACCESS read-only
			STATUS current
			DESCRIPTION
				"Description."
			::= { macFlappingDetectionPortConfigEntry 8 }

		
		-- 1.3.6.1.4.1.34592.1.3.100.15.2.1.9
		macFlappingDetectionPortLinkStatus OBJECT-TYPE
			SYNTAX INTEGER
				{
				down(0),
				up(1),
				protocol-down(2)
				}
			MAX-ACCESS read-only
			STATUS current
			DESCRIPTION
				"Description."
			::= { macFlappingDetectionPortConfigEntry 9 }

		
		-- 1.3.6.1.4.1.34592.1.3.100.15.3
		macFlappingDetectionRecordTable OBJECT-TYPE
			SYNTAX SEQUENCE OF MacFlappingDetectionRecordEntry
			MAX-ACCESS not-accessible
			STATUS current
			DESCRIPTION
				" "
			::= { macFlappingDetectionManagementObjects 3 }

		
		-- 1.3.6.1.4.1.34592.1.3.100.15.3.1
		macFlappingDetectionRecordEntry OBJECT-TYPE
			SYNTAX MacFlappingDetectionRecordEntry
			MAX-ACCESS not-accessible
			STATUS current
			DESCRIPTION
				" "
			INDEX { macFlappingDetectionRecordDeviceIndex, macFlappingDetectionRecordtIndex }
			::= { macFlappingDetectionRecordTable 1 }

		
		MacFlappingDetectionRecordEntry ::=
			SEQUENCE { 
				macFlappingDetectionRecordDeviceIndex
					NscrtvPonExtDeviceIndex,
				macFlappingDetectionRecordtIndex
					Unsigned32,
				macFlappingDetectionRecordOriginalPort
					OCTET STRING,
				macFlappingDetectionRecordMovePort
					OCTET STRING,
				macFlappingDetectionRecordVlanId
					Unsigned32,
				macFlappingDetectionRecordMacAddress
					MacAddress,
				macFlappingDetectionRecordMoveNums
					Unsigned32,
				macFlappingDetectionRecordStartTime
					OCTET STRING,
				macFlappingDetectionRecordEndTime
					OCTET STRING
			 }

		-- 1.3.6.1.4.1.34592.1.3.100.15.3.1.1
		macFlappingDetectionRecordDeviceIndex OBJECT-TYPE
			SYNTAX NscrtvPonExtDeviceIndex
			MAX-ACCESS not-accessible
			STATUS current
			DESCRIPTION
				"OLT设备索引号"
			::= { macFlappingDetectionRecordEntry 1 }

		
		-- 1.3.6.1.4.1.34592.1.3.100.15.3.1.2
		macFlappingDetectionRecordtIndex OBJECT-TYPE
			SYNTAX Unsigned32 (1..8)
			MAX-ACCESS not-accessible
			STATUS current
			DESCRIPTION
				" "
			::= { macFlappingDetectionRecordEntry 2 }

		
		-- 1.3.6.1.4.1.34592.1.3.100.15.3.1.3
		macFlappingDetectionRecordOriginalPort OBJECT-TYPE
			SYNTAX OCTET STRING (SIZE (1..32))
			MAX-ACCESS read-only
			STATUS current
			DESCRIPTION
				" "
			::= { macFlappingDetectionRecordEntry 3 }

		
		-- 1.3.6.1.4.1.34592.1.3.100.15.3.1.4
		macFlappingDetectionRecordMovePort OBJECT-TYPE
			SYNTAX OCTET STRING (SIZE (1..32))
			MAX-ACCESS read-only
			STATUS current
			DESCRIPTION
				" "
			::= { macFlappingDetectionRecordEntry 4 }

		
		-- 1.3.6.1.4.1.34592.1.3.100.15.3.1.5
		macFlappingDetectionRecordVlanId OBJECT-TYPE
			SYNTAX Unsigned32 (1..4094)
			MAX-ACCESS read-only
			STATUS current
			DESCRIPTION
				" "
			::= { macFlappingDetectionRecordEntry 5 }

		
		-- 1.3.6.1.4.1.34592.1.3.100.15.3.1.6
		macFlappingDetectionRecordMacAddress OBJECT-TYPE
			SYNTAX MacAddress
			MAX-ACCESS read-only
			STATUS current
			DESCRIPTION
				" "
			::= { macFlappingDetectionRecordEntry 6 }

		
		-- 1.3.6.1.4.1.34592.1.3.100.15.3.1.7
		macFlappingDetectionRecordMoveNums OBJECT-TYPE
			SYNTAX Unsigned32
			MAX-ACCESS read-only
			STATUS current
			DESCRIPTION
				" "
			::= { macFlappingDetectionRecordEntry 7 }

		
		-- 1.3.6.1.4.1.34592.1.3.100.15.3.1.8
		macFlappingDetectionRecordStartTime OBJECT-TYPE
			SYNTAX OCTET STRING (SIZE (1..32))
			MAX-ACCESS read-only
			STATUS current
			DESCRIPTION
				" "
			::= { macFlappingDetectionRecordEntry 8 }

		
		-- 1.3.6.1.4.1.34592.1.3.100.15.3.1.9
		macFlappingDetectionRecordEndTime OBJECT-TYPE
			SYNTAX OCTET STRING (SIZE (1..32))
			MAX-ACCESS read-only
			STATUS current
			DESCRIPTION
				" "
			::= { macFlappingDetectionRecordEntry 9 }

		
		-- 1.3.6.1.4.1.34592.1.3.100.16
		psgManagementObjects OBJECT IDENTIFIER ::= { nscrtvPonTreeExt 16 }

		
		-- 1.3.6.1.4.1.34592.1.3.100.16.1
		psgTable OBJECT-TYPE
			SYNTAX SEQUENCE OF PsgEntry
			MAX-ACCESS not-accessible
			STATUS current
			DESCRIPTION
				"Description."
			::= { psgManagementObjects 1 }

		
		-- 1.3.6.1.4.1.34592.1.3.100.16.1.1
		psgEntry OBJECT-TYPE
			SYNTAX PsgEntry
			MAX-ACCESS not-accessible
			STATUS current
			DESCRIPTION
				"Description."
			INDEX { psgGroupId }
			::= { psgTable 1 }

		
		PsgEntry ::=
			SEQUENCE { 
				psgGroupId
					Unsigned32,
				psgGroupName
					DisplayString,
				psgProtectType
					INTEGER,
				psgWorkMember
					Unsigned32,
				psgProtectMember
					Unsigned32,
				psgAdminState
					INTEGER,
				psgForceSwitch
					INTEGER,
				psgActiveMember
					Unsigned32,
				psgStandbyMember
					Unsigned32,
				psgOperationStatus
					INTEGER,
				psgStandbyMemberStatus
					INTEGER,
				psgRowStatus
					RowStatus
			 }

		-- 1.3.6.1.4.1.34592.1.3.100.16.1.1.1
		psgGroupId OBJECT-TYPE
			SYNTAX Unsigned32
			MAX-ACCESS not-accessible
			STATUS current
			DESCRIPTION
				"Protect goup id."
			::= { psgEntry 1 }

		
		-- 1.3.6.1.4.1.34592.1.3.100.16.1.1.2
		psgGroupName OBJECT-TYPE
			SYNTAX DisplayString
			MAX-ACCESS read-write
			STATUS current
			DESCRIPTION
				"Protect group name."
			::= { psgEntry 2 }

		
		-- 1.3.6.1.4.1.34592.1.3.100.16.1.1.3
		psgProtectType OBJECT-TYPE
			SYNTAX INTEGER
				{
				typeb(0),
				typec(1)
				}
			MAX-ACCESS read-write
			STATUS current
			DESCRIPTION
				"Protect type.
				typeb : Type B PON protection
				typec : Type C PON protection"
			::= { psgEntry 3 }

		
		-- 1.3.6.1.4.1.34592.1.3.100.16.1.1.4
		psgWorkMember OBJECT-TYPE
			SYNTAX Unsigned32
			MAX-ACCESS read-write
			STATUS current
			DESCRIPTION
				"The work role member of protect group, 
				It is composed of 4 bytes. Each byte from high to low represents device ID, slot ID, port ID, ONU ID. 
				when ONU ID is 0, it means onu id is invalid"
			::= { psgEntry 4 }

		
		-- 1.3.6.1.4.1.34592.1.3.100.16.1.1.5
		psgProtectMember OBJECT-TYPE
			SYNTAX Unsigned32
			MAX-ACCESS read-write
			STATUS current
			DESCRIPTION
				"The protect role member of protect group, 
				It is composed of 4 bytes. Each byte from high to low represents device ID, slot ID, port ID, ONU ID. 
				when ONU ID is 0, it means onu id is invalid."
			::= { psgEntry 5 }

		
		-- 1.3.6.1.4.1.34592.1.3.100.16.1.1.6
		psgAdminState OBJECT-TYPE
			SYNTAX INTEGER
				{
				enable(1),
				disable(2)
				}
			MAX-ACCESS read-write
			STATUS current
			DESCRIPTION
				"Protect group management switch."
			::= { psgEntry 6 }

		
		-- 1.3.6.1.4.1.34592.1.3.100.16.1.1.7
		psgForceSwitch OBJECT-TYPE
			SYNTAX INTEGER
				{
				enable(1),
				disable(2)
				}
			MAX-ACCESS read-write
			STATUS current
			DESCRIPTION
				"Protect group force switch operation."
			::= { psgEntry 7 }

		
		-- 1.3.6.1.4.1.34592.1.3.100.16.1.1.8
		psgActiveMember OBJECT-TYPE
			SYNTAX Unsigned32
			MAX-ACCESS read-only
			STATUS current
			DESCRIPTION
				"Protect group current active members."
			::= { psgEntry 8 }

		
		-- 1.3.6.1.4.1.34592.1.3.100.16.1.1.9
		psgStandbyMember OBJECT-TYPE
			SYNTAX Unsigned32
			MAX-ACCESS read-only
			STATUS current
			DESCRIPTION
				"Protect group current standby members."
			::= { psgEntry 9 }

		
		-- 1.3.6.1.4.1.34592.1.3.100.16.1.1.10
		psgOperationStatus OBJECT-TYPE
			SYNTAX INTEGER
				{
				unknown(0),
				auto(1),
				forceSwitch(2)
				}
			MAX-ACCESS read-only
			STATUS current
			DESCRIPTION
				"Protection group operation status,
				unknown : The state is unknown, such as when protection is disable,
				auto : Automatic switching of protection group occurred,
				forceSwitch : Forced switching is configured."
			::= { psgEntry 10 }

		
		-- 1.3.6.1.4.1.34592.1.3.100.16.1.1.11
		psgStandbyMemberStatus OBJECT-TYPE
			SYNTAX INTEGER
				{
				unknown(0),
				ready(1),
				unreadySignaDetectFailed(2),
				unreadyShutdown(3)
				}
			MAX-ACCESS read-only
			STATUS current
			DESCRIPTION
				"Standby merber status,
				unknown : The state is unknown, such as when protection is disable,
				ready   : Standby merber ready,
				unreadySignaDetectFailed : The standby member could not detect the signal,
				unreadyShutdown : The standby member has been shutdown."
			::= { psgEntry 11 }

		
		-- 1.3.6.1.4.1.34592.1.3.100.16.1.1.12
		psgRowStatus OBJECT-TYPE
			SYNTAX RowStatus
				{
				active(1),
				notInService(2),
				notReady(3),
				createAndGo(4),
				createAndWait(5),
				destroy(6)
				}
			MAX-ACCESS read-create
			STATUS current
			DESCRIPTION
				"Description."
			::= { psgEntry 12 }

		
		-- 1.3.6.1.4.1.34592.1.3.100.17
		hqosManagementObjects OBJECT IDENTIFIER ::= { nscrtvPonTreeExt 17 }

		
		-- 1.3.6.1.4.1.34592.1.3.100.17.1
		hqosCfgTable OBJECT-TYPE
			SYNTAX SEQUENCE OF HqosCfgEntry
			MAX-ACCESS not-accessible
			STATUS current
			DESCRIPTION
				"Description."
			::= { hqosManagementObjects 1 }

		
		-- 1.3.6.1.4.1.34592.1.3.100.17.1.1
		hqosCfgEntry OBJECT-TYPE
			SYNTAX HqosCfgEntry
			MAX-ACCESS not-accessible
			STATUS current
			DESCRIPTION
				"Description."
			INDEX { hqosCfgPortIdIndex, hqosCfgOntIdIndex }
			::= { hqosCfgTable 1 }

		
		HqosCfgEntry ::=
			SEQUENCE { 
				hqosCfgPortIdIndex
					Unsigned32,
				hqosCfgOntIdIndex
					Unsigned32,
				hqosCfgTrafficProfileId
					Unsigned32,
				hqosCfgTrafficProfileName
					DisplayString,
				hqosCfgStatus
					DisplayString,
				hqosCfgTrafficProfileCir
					Unsigned32,
				hqosCfgTrafficProfilePir
					Unsigned32,
				hqosCfgRowStatus
					RowStatus
			 }

		-- 1.3.6.1.4.1.34592.1.3.100.17.1.1.1
		hqosCfgPortIdIndex OBJECT-TYPE
			SYNTAX Unsigned32
			MAX-ACCESS not-accessible
			STATUS current
			DESCRIPTION
				"Description."
			::= { hqosCfgEntry 1 }

		
		-- 1.3.6.1.4.1.34592.1.3.100.17.1.1.2
		hqosCfgOntIdIndex OBJECT-TYPE
			SYNTAX Unsigned32
			MAX-ACCESS not-accessible
			STATUS current
			DESCRIPTION
				"Description."
			::= { hqosCfgEntry 2 }

		
		-- 1.3.6.1.4.1.34592.1.3.100.17.1.1.3
		hqosCfgTrafficProfileId OBJECT-TYPE
			SYNTAX Unsigned32
			MAX-ACCESS read-create
			STATUS current
			DESCRIPTION
				"Description."
			::= { hqosCfgEntry 3 }

		
		-- 1.3.6.1.4.1.34592.1.3.100.17.1.1.4
		hqosCfgTrafficProfileName OBJECT-TYPE
			SYNTAX DisplayString
			MAX-ACCESS read-create
			STATUS current
			DESCRIPTION
				"Description."
			::= { hqosCfgEntry 4 }

		
		-- 1.3.6.1.4.1.34592.1.3.100.17.1.1.5
		hqosCfgStatus OBJECT-TYPE
			SYNTAX DisplayString
			MAX-ACCESS read-only
			STATUS current
			DESCRIPTION
				"Description."
			::= { hqosCfgEntry 5 }

		
		-- 1.3.6.1.4.1.34592.1.3.100.17.1.1.6
		hqosCfgTrafficProfileCir OBJECT-TYPE
			SYNTAX Unsigned32
			MAX-ACCESS read-only
			STATUS current
			DESCRIPTION
				"Description."
			::= { hqosCfgEntry 6 }

		
		-- 1.3.6.1.4.1.34592.1.3.100.17.1.1.7
		hqosCfgTrafficProfilePir OBJECT-TYPE
			SYNTAX Unsigned32
			MAX-ACCESS read-only
			STATUS current
			DESCRIPTION
				"Description."
			::= { hqosCfgEntry 7 }

		
		-- 1.3.6.1.4.1.34592.1.3.100.17.1.1.8
		hqosCfgRowStatus OBJECT-TYPE
			SYNTAX RowStatus
			MAX-ACCESS read-create
			STATUS current
			DESCRIPTION
				"Description."
			::= { hqosCfgEntry 8 }

		
		-- 1.3.6.1.4.1.34592.1.3.100.17.2
		hqosEnable OBJECT-TYPE
			SYNTAX TruthValue
			MAX-ACCESS read-write
			STATUS current
			DESCRIPTION
				"Description."
			::= { hqosManagementObjects 2 }

		
		-- 1.3.6.1.4.1.34592.1.3.100.18
		servicePortEponObjects OBJECT IDENTIFIER ::= { nscrtvPonTreeExt 18 }

		
		-- 1.3.6.1.4.1.34592.1.3.100.18.1
		servicePortEponGlobalInfoTable OBJECT-TYPE
			SYNTAX SEQUENCE OF ServicePortEponGlobalInfoEntry
			MAX-ACCESS not-accessible
			STATUS current
			DESCRIPTION
				"业务虚端口全局信息表"
			::= { servicePortEponObjects 1 }

		
		-- 1.3.6.1.4.1.34592.1.3.100.18.1.1
		servicePortEponGlobalInfoEntry OBJECT-TYPE
			SYNTAX ServicePortEponGlobalInfoEntry
			MAX-ACCESS not-accessible
			STATUS current
			DESCRIPTION
				"Description."
			INDEX { servicePortEponGlobalInfoDeviceIndex, servicePortEponGlobalInfoCardIndex }
			::= { servicePortEponGlobalInfoTable 1 }

		
		ServicePortEponGlobalInfoEntry ::=
			SEQUENCE { 
				servicePortEponGlobalInfoDeviceIndex
					NscrtvPonExtDeviceIndex,
				servicePortEponGlobalInfoCardIndex
					NscrtvPonExtCardIndex,
				servicePortEponGlobalInfoMaxId
					Unsigned32,
				servicePortEponGlobalInfoMaxSupportNumber
					Unsigned32,
				servicePortEponGlobalInfoCreatedNumber
					Unsigned32
			 }

		-- 1.3.6.1.4.1.34592.1.3.100.18.1.1.1
		servicePortEponGlobalInfoDeviceIndex OBJECT-TYPE
			SYNTAX NscrtvPonExtDeviceIndex
			MAX-ACCESS not-accessible
			STATUS current
			DESCRIPTION
				"OLT设备索引号     
				一个OLT节点可以由多台OLT设备组成。节点内的每台OLT设备由OLT设备索引号唯一标识"
			::= { servicePortEponGlobalInfoEntry 1 }

		
		-- 1.3.6.1.4.1.34592.1.3.100.18.1.1.2
		servicePortEponGlobalInfoCardIndex OBJECT-TYPE
			SYNTAX NscrtvPonExtCardIndex
			MAX-ACCESS not-accessible
			STATUS current
			DESCRIPTION
				"板卡索引号"
			::= { servicePortEponGlobalInfoEntry 2 }

		
		-- 1.3.6.1.4.1.34592.1.3.100.18.1.1.3
		servicePortEponGlobalInfoMaxId OBJECT-TYPE
			SYNTAX Unsigned32
			MAX-ACCESS read-only
			STATUS current
			DESCRIPTION
				"当前系统最大业务虚端口编号"
			::= { servicePortEponGlobalInfoEntry 3 }

		
		-- 1.3.6.1.4.1.34592.1.3.100.18.1.1.4
		servicePortEponGlobalInfoMaxSupportNumber OBJECT-TYPE
			SYNTAX Unsigned32
			MAX-ACCESS read-only
			STATUS current
			DESCRIPTION
				"当前系统最大支持的业务虚端口个数"
			::= { servicePortEponGlobalInfoEntry 4 }

		
		-- 1.3.6.1.4.1.34592.1.3.100.18.1.1.5
		servicePortEponGlobalInfoCreatedNumber OBJECT-TYPE
			SYNTAX Unsigned32
			MAX-ACCESS read-only
			STATUS current
			DESCRIPTION
				"当前系统已创建的业务虚端口个数"
			::= { servicePortEponGlobalInfoEntry 5 }

		
		-- 1.3.6.1.4.1.34592.1.3.100.18.2
		servicePortEponCfgInfoTable OBJECT-TYPE
			SYNTAX SEQUENCE OF ServicePortEponCfgInfoEntry
			MAX-ACCESS not-accessible
			STATUS current
			DESCRIPTION
				"业务虚端口配置信息表"
			::= { servicePortEponObjects 2 }

		
		-- 1.3.6.1.4.1.34592.1.3.100.18.2.1
		servicePortEponCfgInfoEntry OBJECT-TYPE
			SYNTAX ServicePortEponCfgInfoEntry
			MAX-ACCESS not-accessible
			STATUS current
			DESCRIPTION
				"Description."
			INDEX { servicePortEponCfgInfoDeviceIndex, servicePortEponCfgInfoCardIndex, servicePortEponCfgInfoIndex }
			::= { servicePortEponCfgInfoTable 1 }

		
		ServicePortEponCfgInfoEntry ::=
			SEQUENCE { 
				servicePortEponCfgInfoDeviceIndex
					NscrtvPonExtDeviceIndex,
				servicePortEponCfgInfoCardIndex
					NscrtvPonExtCardIndex,
				servicePortEponCfgInfoIndex
					Unsigned32,
				servicePortEponCfgInfoSvlanId
					Unsigned32,
				servicePortEponCfgInfoPonPortId
					Unsigned32,
				servicePortEponCfgInfoOnuId
					Unsigned32,
				servicePortEponCfgInfoUserVlanId
					Unsigned32,
				servicePortEponCfgInfoUserVlanPri
					Unsigned32,
				servicePortEponCfgInfoEhterType
					NscrtvPonExtEtherType,
				servicePortEponCfgInfoUpTrafficProfileId
					Unsigned32,
				servicePortEponCfgInfoDownTrafficProfileId
					Unsigned32,
				servicePortEponCfgInfoAdminStatus
					NscrtvPonExtAdminStatus,
				servicePortEponCfgInfoOnuOnlineState
					NscrtvPonExtOnuOnlineState,
				servicePortEponCfgInfoVlanTagAction
					NscrtvPonExtVlanTagAction,
				servicePortEponCfgInfoVlanInnerVid
					Unsigned32,
				servicePortEponCfgInfoVlanInnerPri
					Unsigned32,
				servicePortEponCfgInfoDescription
					OCTET STRING,
				servicePortEponCfgInfoRowStatus
					RowStatus
			 }

		-- 1.3.6.1.4.1.34592.1.3.100.18.2.1.1
		servicePortEponCfgInfoDeviceIndex OBJECT-TYPE
			SYNTAX NscrtvPonExtDeviceIndex
			MAX-ACCESS not-accessible
			STATUS current
			DESCRIPTION
				"OLT设备索引号     
				一个OLT节点可以由多台OLT设备组成。节点内的每台OLT设备由OLT设备索引号唯一标识"
			::= { servicePortEponCfgInfoEntry 1 }

		
		-- 1.3.6.1.4.1.34592.1.3.100.18.2.1.2
		servicePortEponCfgInfoCardIndex OBJECT-TYPE
			SYNTAX NscrtvPonExtCardIndex
			MAX-ACCESS not-accessible
			STATUS current
			DESCRIPTION
				"板卡索引号"
			::= { servicePortEponCfgInfoEntry 2 }

		
		-- 1.3.6.1.4.1.34592.1.3.100.18.2.1.3
		servicePortEponCfgInfoIndex OBJECT-TYPE
			SYNTAX Unsigned32
			MAX-ACCESS not-accessible
			STATUS current
			DESCRIPTION
				"业务虚端口索引号"
			::= { servicePortEponCfgInfoEntry 3 }

		
		-- 1.3.6.1.4.1.34592.1.3.100.18.2.1.4
		servicePortEponCfgInfoSvlanId OBJECT-TYPE
			SYNTAX Unsigned32 (0..4094)
			MAX-ACCESS read-create
			STATUS current
			DESCRIPTION
				"上联口VLAN号
				范围1~4094"
			::= { servicePortEponCfgInfoEntry 4 }

		
		-- 1.3.6.1.4.1.34592.1.3.100.18.2.1.5
		servicePortEponCfgInfoPonPortId OBJECT-TYPE
			SYNTAX Unsigned32 (1..8)
			MAX-ACCESS read-create
			STATUS current
			DESCRIPTION
				"PON端口号
				范围1~8"
			::= { servicePortEponCfgInfoEntry 5 }

		
		-- 1.3.6.1.4.1.34592.1.3.100.18.2.1.6
		servicePortEponCfgInfoOnuId OBJECT-TYPE
			SYNTAX Unsigned32 (1..128)
			MAX-ACCESS read-create
			STATUS current
			DESCRIPTION
				"ONU号
				范围1~128"
			::= { servicePortEponCfgInfoEntry 6 }

		
		-- 1.3.6.1.4.1.34592.1.3.100.18.2.1.7
		servicePortEponCfgInfoUserVlanId OBJECT-TYPE
			SYNTAX Unsigned32 (1..4094)
			MAX-ACCESS read-create
			STATUS current
			DESCRIPTION
				"用户VLAN号
				范围1~4094"
			::= { servicePortEponCfgInfoEntry 7 }

		
		-- 1.3.6.1.4.1.34592.1.3.100.18.2.1.8
		servicePortEponCfgInfoUserVlanPri OBJECT-TYPE
			SYNTAX Unsigned32 (0..7)
			MAX-ACCESS read-create
			STATUS current
			DESCRIPTION
				"用户VLAN优先级
				范围0~7"
			::= { servicePortEponCfgInfoEntry 8 }

		
		-- 1.3.6.1.4.1.34592.1.3.100.18.2.1.9
		servicePortEponCfgInfoEhterType OBJECT-TYPE
			SYNTAX NscrtvPonExtEtherType
			MAX-ACCESS read-create
			STATUS current
			DESCRIPTION
				"用户以太网帧类型
				pppoe 0x8863
				ipv6  0x86dd
				ipv4  0x0800"
			::= { servicePortEponCfgInfoEntry 9 }

		
		-- 1.3.6.1.4.1.34592.1.3.100.18.2.1.10
		servicePortEponCfgInfoUpTrafficProfileId OBJECT-TYPE
			SYNTAX Unsigned32 (0..256)
			MAX-ACCESS read-create
			STATUS current
			DESCRIPTION
				"上行流量模板号
				范围0~256，其中0表示流量模板无效"
			::= { servicePortEponCfgInfoEntry 10 }

		
		-- 1.3.6.1.4.1.34592.1.3.100.18.2.1.11
		servicePortEponCfgInfoDownTrafficProfileId OBJECT-TYPE
			SYNTAX Unsigned32 (0..256)
			MAX-ACCESS read-create
			STATUS current
			DESCRIPTION
				"下行流量模板号
				范围0~256，其中0表示流量模板无效"
			::= { servicePortEponCfgInfoEntry 11 }

		
		-- 1.3.6.1.4.1.34592.1.3.100.18.2.1.12
		servicePortEponCfgInfoAdminStatus OBJECT-TYPE
			SYNTAX NscrtvPonExtAdminStatus
			MAX-ACCESS read-write
			STATUS current
			DESCRIPTION
				"管理状态，0表示失能，1表示使能"
			::= { servicePortEponCfgInfoEntry 12 }

		
		-- 1.3.6.1.4.1.34592.1.3.100.18.2.1.13
		servicePortEponCfgInfoOnuOnlineState OBJECT-TYPE
			SYNTAX NscrtvPonExtOnuOnlineState
			MAX-ACCESS read-only
			STATUS current
			DESCRIPTION
				"ONU在线状态，0表示不在线，1表示在线."
			::= { servicePortEponCfgInfoEntry 13 }

		
		-- 1.3.6.1.4.1.34592.1.3.100.18.2.1.14
		servicePortEponCfgInfoVlanTagAction OBJECT-TYPE
			SYNTAX NscrtvPonExtVlanTagAction
			MAX-ACCESS read-create
			STATUS current
			DESCRIPTION
				"VLAN TAG规则
				范围0~5
				0：default
				1：translate
				2：translate and add
				3：add double
				4：transparent
				5: vlan-transparent
				全透传可配置{5}，不关注SvlanId/UserVlanId
				若UserVlanId无效(单业务)可配置{0,3}
				若UserVlanId有效(多业务)可配置{0,1,2,4}"
			::= { servicePortEponCfgInfoEntry 14 }

		
		-- 1.3.6.1.4.1.34592.1.3.100.18.2.1.15
		servicePortEponCfgInfoVlanInnerVid OBJECT-TYPE
			SYNTAX Unsigned32 (1..4094)
			MAX-ACCESS read-create
			STATUS current
			DESCRIPTION
				"VLAN翻译内层VLAN号
				范围1~4094
				仅当VLAN TAG规则为{2,3}有效."
			::= { servicePortEponCfgInfoEntry 15 }

		
		-- 1.3.6.1.4.1.34592.1.3.100.18.2.1.16
		servicePortEponCfgInfoVlanInnerPri OBJECT-TYPE
			SYNTAX Unsigned32 (0..7)
			MAX-ACCESS read-create
			STATUS current
			DESCRIPTION
				"VLAN翻译内层VLAN优先级
				范围0~7
				仅当VLAN TAG规则为{2,3}有效"
			::= { servicePortEponCfgInfoEntry 16 }

		
		-- 1.3.6.1.4.1.34592.1.3.100.18.2.1.17
		servicePortEponCfgInfoDescription OBJECT-TYPE
			SYNTAX OCTET STRING (SIZE (0..64))
			MAX-ACCESS read-write
			STATUS current
			DESCRIPTION
				"描述信息"
			::= { servicePortEponCfgInfoEntry 17 }

		
		-- 1.3.6.1.4.1.34592.1.3.100.18.2.1.18
		servicePortEponCfgInfoRowStatus OBJECT-TYPE
			SYNTAX RowStatus
			MAX-ACCESS read-create
			STATUS current
			DESCRIPTION
				"行状态"
			::= { servicePortEponCfgInfoEntry 18 }

		
		-- 1.3.6.1.4.1.34592.1.3.100.18.3
		servicePortEponAutoCfgInfoTable OBJECT-TYPE
			SYNTAX SEQUENCE OF ServicePortEponAutoCfgInfoEntry
			MAX-ACCESS not-accessible
			STATUS current
			DESCRIPTION
				"业务虚端口自动配置信息表"
			::= { servicePortEponObjects 3 }

		
		-- 1.3.6.1.4.1.34592.1.3.100.18.3.1
		servicePortEponAutoCfgInfoEntry OBJECT-TYPE
			SYNTAX ServicePortEponAutoCfgInfoEntry
			MAX-ACCESS not-accessible
			STATUS current
			DESCRIPTION
				"Description."
			INDEX { servicePortEponAutoCfgInfoDeviceIndex, servicePortEponAutoCfgInfoCardIndex, servicePortEponAutoCfgInfoPonPortIndex }
			::= { servicePortEponAutoCfgInfoTable 1 }

		
		ServicePortEponAutoCfgInfoEntry ::=
			SEQUENCE { 
				servicePortEponAutoCfgInfoDeviceIndex
					NscrtvPonExtDeviceIndex,
				servicePortEponAutoCfgInfoCardIndex
					NscrtvPonExtCardIndex,
				servicePortEponAutoCfgInfoPonPortIndex
					Unsigned32,
				servicePortEponAutoCfgInfoSvlanId
					Unsigned32,
				servicePortEponAutoCfgInfoUserVlanId
					Unsigned32,
				servicePortEponAutoCfgInfoVlanTagAction
					NscrtvPonExtVlanTagAction,
				servicePortEponAutoCfgInfoVlanInnerVid
					Unsigned32,
				servicePortEponAutoCfgInfoVlanInnerPri
					Unsigned32,
				servicePortEponAutoCfgInfoUpTrafficProfileId
					Unsigned32,
				servicePortEponAutoCfgInfoDownTrafficProfileId
					Unsigned32,
				servicePortEponAutoCfgInfoMode
					NscrtvPonExtAutoMode
			 }

		-- 1.3.6.1.4.1.34592.1.3.100.18.3.1.1
		servicePortEponAutoCfgInfoDeviceIndex OBJECT-TYPE
			SYNTAX NscrtvPonExtDeviceIndex
			MAX-ACCESS not-accessible
			STATUS current
			DESCRIPTION
				"OLT设备索引号        
				一个OLT节点可以由多台OLT设备组成。节点内的每台OLT设备由OLT设备索引号唯一标识"
			::= { servicePortEponAutoCfgInfoEntry 1 }

		
		-- 1.3.6.1.4.1.34592.1.3.100.18.3.1.2
		servicePortEponAutoCfgInfoCardIndex OBJECT-TYPE
			SYNTAX NscrtvPonExtCardIndex
			MAX-ACCESS not-accessible
			STATUS current
			DESCRIPTION
				"板卡索引号"
			::= { servicePortEponAutoCfgInfoEntry 2 }

		
		-- 1.3.6.1.4.1.34592.1.3.100.18.3.1.3
		servicePortEponAutoCfgInfoPonPortIndex OBJECT-TYPE
			SYNTAX Unsigned32
			MAX-ACCESS not-accessible
			STATUS current
			DESCRIPTION
				"PON端口索引号，范围1~8"
			::= { servicePortEponAutoCfgInfoEntry 3 }

		
		-- 1.3.6.1.4.1.34592.1.3.100.18.3.1.4
		servicePortEponAutoCfgInfoSvlanId OBJECT-TYPE
			SYNTAX Unsigned32 (1..4094)
			MAX-ACCESS read-write
			STATUS current
			DESCRIPTION
				"上联口VLAN号
				范围1~4094"
			::= { servicePortEponAutoCfgInfoEntry 4 }

		
		-- 1.3.6.1.4.1.34592.1.3.100.18.3.1.5
		servicePortEponAutoCfgInfoUserVlanId OBJECT-TYPE
			SYNTAX Unsigned32 (0..4094)
			MAX-ACCESS read-write
			STATUS current
			DESCRIPTION
				"用户VLAN号
				范围0~4094，若为0表示用户VLAN无效"
			::= { servicePortEponAutoCfgInfoEntry 5 }

		
		-- 1.3.6.1.4.1.34592.1.3.100.18.3.1.6
		servicePortEponAutoCfgInfoVlanTagAction OBJECT-TYPE
			SYNTAX NscrtvPonExtVlanTagAction
			MAX-ACCESS read-write
			STATUS current
			DESCRIPTION
				"VLAN TAG规则
				范围0~5
				0：default
				1：translate
				2：translate and add
				3：add double
				4：transparent
				5: vlan-transparent
				全透传可配置{5}，不关注SvlanId/UserVlanId
				若UserVlanId无效(单业务)可配置{0,3}
				若UserVlanId有效(多业务)可配置{0,1,2,4}"
			::= { servicePortEponAutoCfgInfoEntry 6 }

		
		-- 1.3.6.1.4.1.34592.1.3.100.18.3.1.7
		servicePortEponAutoCfgInfoVlanInnerVid OBJECT-TYPE
			SYNTAX Unsigned32 (1..4094)
			MAX-ACCESS read-write
			STATUS current
			DESCRIPTION
				"VLAN翻译内层VLAN号
				范围1~4094
				仅当VLAN TAG规则为{2,3}有效"
			::= { servicePortEponAutoCfgInfoEntry 7 }

		
		-- 1.3.6.1.4.1.34592.1.3.100.18.3.1.8
		servicePortEponAutoCfgInfoVlanInnerPri OBJECT-TYPE
			SYNTAX Unsigned32 (0..7)
			MAX-ACCESS read-write
			STATUS current
			DESCRIPTION
				"VLAN翻译内层VLAN优先级
				范围0~7
				仅当VLAN TAG规则为{2,3}有效"
			::= { servicePortEponAutoCfgInfoEntry 8 }

		
		-- 1.3.6.1.4.1.34592.1.3.100.18.3.1.9
		servicePortEponAutoCfgInfoUpTrafficProfileId OBJECT-TYPE
			SYNTAX Unsigned32 (0..256)
			MAX-ACCESS read-write
			STATUS current
			DESCRIPTION
				"上行流量模板号
				范围0~256，其中0表示流量模板无效"
			::= { servicePortEponAutoCfgInfoEntry 9 }

		
		-- 1.3.6.1.4.1.34592.1.3.100.18.3.1.10
		servicePortEponAutoCfgInfoDownTrafficProfileId OBJECT-TYPE
			SYNTAX Unsigned32 (0..256)
			MAX-ACCESS read-write
			STATUS current
			DESCRIPTION
				"下行流量模板号
				范围0~256，其中0表示流量模板无效"
			::= { servicePortEponAutoCfgInfoEntry 10 }

		
		-- 1.3.6.1.4.1.34592.1.3.100.18.3.1.11
		servicePortEponAutoCfgInfoMode OBJECT-TYPE
			SYNTAX NscrtvPonExtAutoMode
			MAX-ACCESS read-write
			STATUS current
			DESCRIPTION
				"自动配置模式
				范围0~1,0表示自动模式，1表示手动模式"
			::= { servicePortEponAutoCfgInfoEntry 11 }

		
		-- 1.3.6.1.4.1.34592.1.3.100.19
		igmpManagementExtObjects OBJECT IDENTIFIER ::= { nscrtvPonTreeExt 19 }

		
		-- 1.3.6.1.4.1.34592.1.3.100.19.1
		igmpGlobalTable OBJECT-TYPE
			SYNTAX SEQUENCE OF IgmpGlobalEntry
			MAX-ACCESS not-accessible
			STATUS current
			DESCRIPTION
				"Description."
			::= { igmpManagementExtObjects 1 }

		
		-- 1.3.6.1.4.1.34592.1.3.100.19.1.1
		igmpGlobalEntry OBJECT-TYPE
			SYNTAX IgmpGlobalEntry
			MAX-ACCESS not-accessible
			STATUS current
			DESCRIPTION
				"Description."
			INDEX { igmpDeviceIndex }
			::= { igmpGlobalTable 1 }

		
		IgmpGlobalEntry ::=
			SEQUENCE { 
				igmpDeviceIndex
					Integer32,
				igmpGlobalMode
					INTEGER,
				igmpGlobalQuerier
					INTEGER,
				igmpGlobalGeneralQueryInterval
					Integer32,
				igmpGlobalRobustness
					Integer32,
				igmpGlobalGeneralQueryResponse
					Integer32,
				igmpGlobalSpecificQueryInterval
					Integer32,
				igmpGlobalSpecificQueryCount
					Integer32,
				igmpGlobalSpecificQueryResponse
					Integer32,
				igmpGlobalQuerySourceIP
					IpAddress,
				igmpGlobalIgmpPolicy
					INTEGER,
				igmpGlobalFastLeave
					INTEGER,
				igmpGlobalVersion
					INTEGER
			 }

		-- 1.3.6.1.4.1.34592.1.3.100.19.1.1.1
		igmpDeviceIndex OBJECT-TYPE
			SYNTAX Integer32
			MAX-ACCESS read-only
			STATUS current
			DESCRIPTION
				"Description."
			::= { igmpGlobalEntry 1 }

		
		-- 1.3.6.1.4.1.34592.1.3.100.19.1.1.2
		igmpGlobalMode OBJECT-TYPE
			SYNTAX INTEGER
				{
				disable(0),
				proxy(1),
				snooping(2)
				}
			MAX-ACCESS read-write
			STATUS current
			DESCRIPTION
				"Description."
			::= { igmpGlobalEntry 2 }

		
		-- 1.3.6.1.4.1.34592.1.3.100.19.1.1.3
		igmpGlobalQuerier OBJECT-TYPE
			SYNTAX INTEGER
				{
				disable(0),
				enable(1)
				}
			MAX-ACCESS read-write
			STATUS current
			DESCRIPTION
				"Description."
			::= { igmpGlobalEntry 3 }

		
		-- 1.3.6.1.4.1.34592.1.3.100.19.1.1.4
		igmpGlobalGeneralQueryInterval OBJECT-TYPE
			SYNTAX Integer32
			MAX-ACCESS read-write
			STATUS current
			DESCRIPTION
				"Description."
			::= { igmpGlobalEntry 4 }

		
		-- 1.3.6.1.4.1.34592.1.3.100.19.1.1.5
		igmpGlobalRobustness OBJECT-TYPE
			SYNTAX Integer32
			MAX-ACCESS read-write
			STATUS current
			DESCRIPTION
				"Description."
			::= { igmpGlobalEntry 5 }

		
		-- 1.3.6.1.4.1.34592.1.3.100.19.1.1.6
		igmpGlobalGeneralQueryResponse OBJECT-TYPE
			SYNTAX Integer32
			MAX-ACCESS read-write
			STATUS current
			DESCRIPTION
				"Description."
			::= { igmpGlobalEntry 6 }

		
		-- 1.3.6.1.4.1.34592.1.3.100.19.1.1.7
		igmpGlobalSpecificQueryInterval OBJECT-TYPE
			SYNTAX Integer32
			MAX-ACCESS read-write
			STATUS current
			DESCRIPTION
				"Description."
			::= { igmpGlobalEntry 7 }

		
		-- 1.3.6.1.4.1.34592.1.3.100.19.1.1.8
		igmpGlobalSpecificQueryCount OBJECT-TYPE
			SYNTAX Integer32
			MAX-ACCESS read-write
			STATUS current
			DESCRIPTION
				"Description."
			::= { igmpGlobalEntry 8 }

		
		-- 1.3.6.1.4.1.34592.1.3.100.19.1.1.9
		igmpGlobalSpecificQueryResponse OBJECT-TYPE
			SYNTAX Integer32
			MAX-ACCESS read-write
			STATUS current
			DESCRIPTION
				"Description."
			::= { igmpGlobalEntry 9 }

		
		-- 1.3.6.1.4.1.34592.1.3.100.19.1.1.10
		igmpGlobalQuerySourceIP OBJECT-TYPE
			SYNTAX IpAddress
			MAX-ACCESS read-write
			STATUS current
			DESCRIPTION
				"Description."
			::= { igmpGlobalEntry 10 }

		
		-- 1.3.6.1.4.1.34592.1.3.100.19.1.1.11
		igmpGlobalIgmpPolicy OBJECT-TYPE
			SYNTAX INTEGER
				{
				pass(0),
				discard(1)
				}
			MAX-ACCESS read-write
			STATUS current
			DESCRIPTION
				"Description."
			::= { igmpGlobalEntry 11 }

		
		-- 1.3.6.1.4.1.34592.1.3.100.19.1.1.12
		igmpGlobalFastLeave OBJECT-TYPE
			SYNTAX INTEGER
				{
				disable(0),
				enable(1)
				}
			MAX-ACCESS read-write
			STATUS current
			DESCRIPTION
				"Description."
			::= { igmpGlobalEntry 12 }

		
		-- 1.3.6.1.4.1.34592.1.3.100.19.1.1.13
		igmpGlobalVersion OBJECT-TYPE
			SYNTAX INTEGER
				{
				v1(0),
				v2(1),
				v3(2)
				}
			MAX-ACCESS read-write
			STATUS current
			DESCRIPTION
				"Description."
			::= { igmpGlobalEntry 13 }

		
		-- 1.3.6.1.4.1.34592.1.3.100.19.2
		igmpStaticForwardingTable OBJECT-TYPE
			SYNTAX SEQUENCE OF IgmpStaticForwardingEntry
			MAX-ACCESS not-accessible
			STATUS current
			DESCRIPTION
				"
				Multicast forwarding table        
				"
			::= { igmpManagementExtObjects 2 }

		
		-- 1.3.6.1.4.1.34592.1.3.100.19.2.1
		igmpStaticForwardingEntry OBJECT-TYPE
			SYNTAX IgmpStaticForwardingEntry
			MAX-ACCESS not-accessible
			STATUS current
			DESCRIPTION
				" "
			INDEX { staticGroupDeviceIndex, staticGroupVlanIndex, staticGroupIPAddress }
			::= { igmpStaticForwardingTable 1 }

		
		IgmpStaticForwardingEntry ::=
			SEQUENCE { 
				staticGroupDeviceIndex
					INTEGER,
				staticGroupVlanIndex
					INTEGER,
				staticGroupIPAddress
					IpAddress,
				staticGroupPortList
					OCTET STRING,
				staticGroupRowStatus
					RowStatus
			 }

		-- 1.3.6.1.4.1.34592.1.3.100.19.2.1.1
		staticGroupDeviceIndex OBJECT-TYPE
			SYNTAX INTEGER
			MAX-ACCESS not-accessible
			STATUS current
			DESCRIPTION
				"
				设备索引号。        
				For OLT Agent, set to corresponding OLT device
				For ONU Agent, set to 0
				"
			::= { igmpStaticForwardingEntry 1 }

		
		-- 1.3.6.1.4.1.34592.1.3.100.19.2.1.2
		staticGroupVlanIndex OBJECT-TYPE
			SYNTAX INTEGER
			MAX-ACCESS not-accessible
			STATUS current
			DESCRIPTION
				"
				Vlan索引号"
			::= { igmpStaticForwardingEntry 2 }

		
		-- 1.3.6.1.4.1.34592.1.3.100.19.2.1.3
		staticGroupIPAddress OBJECT-TYPE
			SYNTAX IpAddress
			MAX-ACCESS not-accessible
			STATUS current
			DESCRIPTION
				"
				组IP地址索引号"
			::= { igmpStaticForwardingEntry 3 }

		
		-- 1.3.6.1.4.1.34592.1.3.100.19.2.1.4
		staticGroupPortList OBJECT-TYPE
			SYNTAX OCTET STRING
			MAX-ACCESS read-create
			STATUS current
			DESCRIPTION
				"
				Forwarding port list
				1. OLT
				-------------------------------------------------------------------
				It is presented by member port list. Each member port is identified
				by 4-byte format, same as TC of EponDeviceIndex. The actual length of
				this string depends of the number of member ports in the port list.
				The relationship is:
				Length of the string = 4 * (NUM of member ports)  
				For example, if device 1, port 1/2 and 2/3 is the member ports, 
				then this object will be presented as:
				01 01 02 00 01 02 03 00
				
				2. ONU
				-------------------------------------------------------------------
				It is presented by member port list. Each member port is identified
				by 2-byte format, One for slot ID, the last for port ID. The actual 
				length of this string depends of the number of member ports. If the 
				ONU is fixed (not modulized), set slot ID to 0, the NMS could ignore 
				the slot info.
				Note that, slot here shall follow the last byte definition of 
				EponCardIndex to indicate the main-slot and sub-slot index.  
				The relationship is:
				Length of the string = 2 * (NUM of member ports)  
				For example, if port 1/2 and 3/4 is the member ports of the group, 
				then the object is presented as:
				01 02 03 04       
				"
			::= { igmpStaticForwardingEntry 4 }

		
		-- 1.3.6.1.4.1.34592.1.3.100.19.2.1.5
		staticGroupRowStatus OBJECT-TYPE
			SYNTAX RowStatus
			MAX-ACCESS read-create
			STATUS current
			DESCRIPTION
				"行状态"
			::= { igmpStaticForwardingEntry 5 }

		
		-- 1.3.6.1.4.1.34592.1.3.100.19.3
		igmpMulticastVlanExtTable OBJECT-TYPE
			SYNTAX SEQUENCE OF IgmpMulticastVlanExtEntry
			MAX-ACCESS not-accessible
			STATUS current
			DESCRIPTION
				"Description."
			::= { igmpManagementExtObjects 3 }

		
		-- 1.3.6.1.4.1.34592.1.3.100.19.3.1
		igmpMulticastVlanExtEntry OBJECT-TYPE
			SYNTAX IgmpMulticastVlanExtEntry
			MAX-ACCESS not-accessible
			STATUS current
			DESCRIPTION
				"Description."
			INDEX { mVlanDeviceIndex }
			::= { igmpMulticastVlanExtTable 1 }

		
		IgmpMulticastVlanExtEntry ::=
			SEQUENCE { 
				mVlanDeviceIndex
					INTEGER,
				mVlanId
					Integer32,
				mVlanUnknownPolicy
					INTEGER
			 }

		-- 1.3.6.1.4.1.34592.1.3.100.19.3.1.1
		mVlanDeviceIndex OBJECT-TYPE
			SYNTAX INTEGER
			MAX-ACCESS read-only
			STATUS current
			DESCRIPTION
				"Description."
			::= { igmpMulticastVlanExtEntry 1 }

		
		-- 1.3.6.1.4.1.34592.1.3.100.19.3.1.2
		mVlanId OBJECT-TYPE
			SYNTAX Integer32
			MAX-ACCESS read-only
			STATUS current
			DESCRIPTION
				"Description."
			::= { igmpMulticastVlanExtEntry 2 }

		
		-- 1.3.6.1.4.1.34592.1.3.100.19.3.1.3
		mVlanUnknownPolicy OBJECT-TYPE
			SYNTAX INTEGER
				{
				transparent(0),
				discard(1)
				}
			MAX-ACCESS read-write
			STATUS current
			DESCRIPTION
				"Description."
			::= { igmpMulticastVlanExtEntry 3 }

		
		-- 1.3.6.1.4.1.34592.1.3.100.19.4
		igmpProgramTable OBJECT-TYPE
			SYNTAX SEQUENCE OF IgmpProgramEntry
			MAX-ACCESS not-accessible
			STATUS current
			DESCRIPTION
				"Description."
			::= { igmpManagementExtObjects 4 }

		
		-- 1.3.6.1.4.1.34592.1.3.100.19.4.1
		igmpProgramEntry OBJECT-TYPE
			SYNTAX IgmpProgramEntry
			MAX-ACCESS not-accessible
			STATUS current
			DESCRIPTION
				"Description."
			INDEX { igmpProgramIndex }
			::= { igmpProgramTable 1 }

		
		IgmpProgramEntry ::=
			SEQUENCE { 
				igmpProgramIndex
					Integer32,
				igmpProgramVlanId
					Unsigned32,
				igmpProgramStartIp
					IpAddress,
				igmpProgramToIp
					IpAddress,
				igmpProgramRowStatus
					RowStatus
			 }

		-- 1.3.6.1.4.1.34592.1.3.100.19.4.1.1
		igmpProgramIndex OBJECT-TYPE
			SYNTAX Integer32
			MAX-ACCESS read-only
			STATUS current
			DESCRIPTION
				"Description."
			::= { igmpProgramEntry 1 }

		
		-- 1.3.6.1.4.1.34592.1.3.100.19.4.1.2
		igmpProgramVlanId OBJECT-TYPE
			SYNTAX Unsigned32
			MAX-ACCESS read-create
			STATUS current
			DESCRIPTION
				"Description."
			::= { igmpProgramEntry 2 }

		
		-- 1.3.6.1.4.1.34592.1.3.100.19.4.1.3
		igmpProgramStartIp OBJECT-TYPE
			SYNTAX IpAddress
			MAX-ACCESS read-create
			STATUS current
			DESCRIPTION
				"Description."
			::= { igmpProgramEntry 3 }

		
		-- 1.3.6.1.4.1.34592.1.3.100.19.4.1.4
		igmpProgramToIp OBJECT-TYPE
			SYNTAX IpAddress
			MAX-ACCESS read-create
			STATUS current
			DESCRIPTION
				"Description."
			::= { igmpProgramEntry 4 }

		
		-- 1.3.6.1.4.1.34592.1.3.100.19.4.1.5
		igmpProgramRowStatus OBJECT-TYPE
			SYNTAX RowStatus
			MAX-ACCESS read-create
			STATUS current
			DESCRIPTION
				"Description."
			::= { igmpProgramEntry 5 }

		
		-- 1.3.6.1.4.1.34592.1.3.100.20
		stpExtManagementObjects OBJECT IDENTIFIER ::= { nscrtvPonTreeExt 20 }

		
		-- 1.3.6.1.4.1.34592.1.3.100.20.1
		stpPortExtTable OBJECT-TYPE
			SYNTAX SEQUENCE OF StpPortExtEntry
			MAX-ACCESS not-accessible
			STATUS current
			DESCRIPTION
				"Description."
			::= { stpExtManagementObjects 1 }

		
		-- 1.3.6.1.4.1.34592.1.3.100.20.1.1
		stpPortExtEntry OBJECT-TYPE
			SYNTAX StpPortExtEntry
			MAX-ACCESS not-accessible
			STATUS current
			DESCRIPTION
				"Description."
			INDEX { stpPortExtStpIndex, stpPortExtCardIndex, stpPortExtIndex }
			::= { stpPortExtTable 1 }

		
		StpPortExtEntry ::=
			SEQUENCE { 
				stpPortExtStpIndex
					Integer32,
				stpPortExtCardIndex
					Integer32,
				stpPortExtIndex
					Integer32,
				stpPortExtRole
					INTEGER
			 }

		-- 1.3.6.1.4.1.34592.1.3.100.20.1.1.1
		stpPortExtStpIndex OBJECT-TYPE
			SYNTAX Integer32
			MAX-ACCESS read-only
			STATUS current
			DESCRIPTION
				"Description."
			::= { stpPortExtEntry 1 }

		
		-- 1.3.6.1.4.1.34592.1.3.100.20.1.1.2
		stpPortExtCardIndex OBJECT-TYPE
			SYNTAX Integer32
			MAX-ACCESS read-only
			STATUS current
			DESCRIPTION
				"Description."
			::= { stpPortExtEntry 2 }

		
		-- 1.3.6.1.4.1.34592.1.3.100.20.1.1.3
		stpPortExtIndex OBJECT-TYPE
			SYNTAX Integer32
			MAX-ACCESS read-only
			STATUS current
			DESCRIPTION
				"Description."
			::= { stpPortExtEntry 3 }

		
		-- 1.3.6.1.4.1.34592.1.3.100.20.1.1.4
		stpPortExtRole OBJECT-TYPE
			SYNTAX INTEGER
				{
				Unknown(0),
				Alternate(1),
				Root(2),
				Designated(3),
				Backup(4),
				Disable(5)
				}
			MAX-ACCESS read-only
			STATUS current
			DESCRIPTION
				"Description."
			::= { stpPortExtEntry 4 }

		
		-- 1.3.6.1.4.1.34592.1.3.100.20.2
		stpExtGlobalBaseTable OBJECT-TYPE
			SYNTAX SEQUENCE OF StpExtGlobalBaseEntry
			MAX-ACCESS not-accessible
			STATUS current
			DESCRIPTION
				"Description."
			::= { stpExtManagementObjects 2 }

		
		-- 1.3.6.1.4.1.34592.1.3.100.20.2.1
		stpExtGlobalBaseEntry OBJECT-TYPE
			SYNTAX StpExtGlobalBaseEntry
			MAX-ACCESS not-accessible
			STATUS current
			DESCRIPTION
				"Description."
			INDEX { stpExtGlobalBaseDeviceIndex }
			::= { stpExtGlobalBaseTable 1 }

		
		StpExtGlobalBaseEntry ::=
			SEQUENCE { 
				stpExtGlobalBaseDeviceIndex
					NscrtvPonExtDeviceIndex,
				stpExtGlobalBaseEnable
					INTEGER,
				stpExtGlobalBaseVersion
					INTEGER,
				stpExtGlobalBaseForwardDelay
					Unsigned32,
				stpExtGlobalBaseHelloTime
					Unsigned32,
				stpExtGlobalBaseMaxAge
					Unsigned32,
				stpExtGlobalBaseMaxHops
					Unsigned32,
				stpExtGlobalBaseHoldCount
					Unsigned32,
				stpExtGlobalBaseRecovery
					Unsigned32,
				stpExtGlobalBaseBpduGuard
					INTEGER,
				stpExtGlobalBaseBpduFilter
					INTEGER,
				stpExtGlobalBasePathCostStandard
					INTEGER,
				stpExtGlobalBaseRegionName
					DisplayString,
				stpExtGlobalBaseRegionRevision
					Unsigned32
			 }

		-- 1.3.6.1.4.1.34592.1.3.100.20.2.1.1
		stpExtGlobalBaseDeviceIndex OBJECT-TYPE
			SYNTAX NscrtvPonExtDeviceIndex
			MAX-ACCESS not-accessible
			STATUS current
			DESCRIPTION
				"Description."
			::= { stpExtGlobalBaseEntry 1 }

		
		-- 1.3.6.1.4.1.34592.1.3.100.20.2.1.2
		stpExtGlobalBaseEnable OBJECT-TYPE
			SYNTAX INTEGER
				{
				disable(0),
				enable(1)
				}
			MAX-ACCESS read-write
			STATUS current
			DESCRIPTION
				"Description."
			::= { stpExtGlobalBaseEntry 2 }

		
		-- 1.3.6.1.4.1.34592.1.3.100.20.2.1.3
		stpExtGlobalBaseVersion OBJECT-TYPE
			SYNTAX INTEGER
				{
				stp(0),
				rstp(2),
				mstp(3)
				}
			MAX-ACCESS read-write
			STATUS current
			DESCRIPTION
				"Description."
			::= { stpExtGlobalBaseEntry 3 }

		
		-- 1.3.6.1.4.1.34592.1.3.100.20.2.1.4
		stpExtGlobalBaseForwardDelay OBJECT-TYPE
			SYNTAX Unsigned32 (4..30)
			MAX-ACCESS read-write
			STATUS current
			DESCRIPTION
				"Description."
			::= { stpExtGlobalBaseEntry 4 }

		
		-- 1.3.6.1.4.1.34592.1.3.100.20.2.1.5
		stpExtGlobalBaseHelloTime OBJECT-TYPE
			SYNTAX Unsigned32 (1..10)
			MAX-ACCESS read-write
			STATUS current
			DESCRIPTION
				"Description."
			::= { stpExtGlobalBaseEntry 5 }

		
		-- 1.3.6.1.4.1.34592.1.3.100.20.2.1.6
		stpExtGlobalBaseMaxAge OBJECT-TYPE
			SYNTAX Unsigned32 (4..30)
			MAX-ACCESS read-write
			STATUS current
			DESCRIPTION
				"Description."
			::= { stpExtGlobalBaseEntry 6 }

		
		-- 1.3.6.1.4.1.34592.1.3.100.20.2.1.7
		stpExtGlobalBaseMaxHops OBJECT-TYPE
			SYNTAX Unsigned32 (6..40)
			MAX-ACCESS read-write
			STATUS current
			DESCRIPTION
				"Description."
			::= { stpExtGlobalBaseEntry 7 }

		
		-- 1.3.6.1.4.1.34592.1.3.100.20.2.1.8
		stpExtGlobalBaseHoldCount OBJECT-TYPE
			SYNTAX Unsigned32 (1..10)
			MAX-ACCESS read-write
			STATUS current
			DESCRIPTION
				"Description."
			::= { stpExtGlobalBaseEntry 8 }

		
		-- 1.3.6.1.4.1.34592.1.3.100.20.2.1.9
		stpExtGlobalBaseRecovery OBJECT-TYPE
			SYNTAX Unsigned32 (30..86400)
			MAX-ACCESS read-write
			STATUS current
			DESCRIPTION
				"Description."
			::= { stpExtGlobalBaseEntry 9 }

		
		-- 1.3.6.1.4.1.34592.1.3.100.20.2.1.10
		stpExtGlobalBaseBpduGuard OBJECT-TYPE
			SYNTAX INTEGER
				{
				disable(0),
				enable(1)
				}
			MAX-ACCESS read-write
			STATUS current
			DESCRIPTION
				"Description."
			::= { stpExtGlobalBaseEntry 10 }

		
		-- 1.3.6.1.4.1.34592.1.3.100.20.2.1.11
		stpExtGlobalBaseBpduFilter OBJECT-TYPE
			SYNTAX INTEGER
				{
				disable(0),
				enable(1)
				}
			MAX-ACCESS read-write
			STATUS current
			DESCRIPTION
				"Description."
			::= { stpExtGlobalBaseEntry 11 }

		
		-- 1.3.6.1.4.1.34592.1.3.100.20.2.1.12
		stpExtGlobalBasePathCostStandard OBJECT-TYPE
			SYNTAX INTEGER
				{
				dot1t(0),
				dot1d(1),
				legacy(2)
				}
			MAX-ACCESS read-write
			STATUS current
			DESCRIPTION
				"Description."
			::= { stpExtGlobalBaseEntry 12 }

		
		-- 1.3.6.1.4.1.34592.1.3.100.20.2.1.13
		stpExtGlobalBaseRegionName OBJECT-TYPE
			SYNTAX DisplayString (SIZE (0..31))
			MAX-ACCESS read-write
			STATUS current
			DESCRIPTION
				"Description."
			::= { stpExtGlobalBaseEntry 13 }

		
		-- 1.3.6.1.4.1.34592.1.3.100.20.2.1.14
		stpExtGlobalBaseRegionRevision OBJECT-TYPE
			SYNTAX Unsigned32 (0..65535)
			MAX-ACCESS read-write
			STATUS current
			DESCRIPTION
				"Description."
			::= { stpExtGlobalBaseEntry 14 }

		
		-- 1.3.6.1.4.1.34592.1.3.100.20.3
		stpExtGlobalInstanceTable OBJECT-TYPE
			SYNTAX SEQUENCE OF StpExtGlobalInstanceEntry
			MAX-ACCESS not-accessible
			STATUS current
			DESCRIPTION
				"Description."
			::= { stpExtManagementObjects 3 }

		
		-- 1.3.6.1.4.1.34592.1.3.100.20.3.1
		stpExtGlobalInstanceEntry OBJECT-TYPE
			SYNTAX StpExtGlobalInstanceEntry
			MAX-ACCESS not-accessible
			STATUS current
			DESCRIPTION
				"Description."
			INDEX { stpExtGlobalInstanceIndex }
			::= { stpExtGlobalInstanceTable 1 }

		
		StpExtGlobalInstanceEntry ::=
			SEQUENCE { 
				stpExtGlobalInstanceIndex
					Unsigned32,
				stpExtGlobalInstancePriority
					Unsigned32,
				stpExtGlobalInstanceVlanList
					OCTET STRING
			 }

		-- 1.3.6.1.4.1.34592.1.3.100.20.3.1.1
		stpExtGlobalInstanceIndex OBJECT-TYPE
			SYNTAX Unsigned32 (0..7)
			MAX-ACCESS not-accessible
			STATUS current
			DESCRIPTION
				"Description."
			::= { stpExtGlobalInstanceEntry 1 }

		
		-- 1.3.6.1.4.1.34592.1.3.100.20.3.1.2
		stpExtGlobalInstancePriority OBJECT-TYPE
			SYNTAX Unsigned32 (0..65535)
			MAX-ACCESS read-write
			STATUS current
			DESCRIPTION
				"Description."
			::= { stpExtGlobalInstanceEntry 2 }

		
		-- 1.3.6.1.4.1.34592.1.3.100.20.3.1.3
		stpExtGlobalInstanceVlanList OBJECT-TYPE
			SYNTAX OCTET STRING (SIZE (512))
			MAX-ACCESS read-write
			STATUS current
			DESCRIPTION
				"Description."
			::= { stpExtGlobalInstanceEntry 3 }

		
		-- 1.3.6.1.4.1.34592.1.3.100.20.4
		stpExtPortBaseTable OBJECT-TYPE
			SYNTAX SEQUENCE OF StpExtPortBaseEntry
			MAX-ACCESS not-accessible
			STATUS current
			DESCRIPTION
				"Description."
			::= { stpExtManagementObjects 4 }

		
		-- 1.3.6.1.4.1.34592.1.3.100.20.4.1
		stpExtPortBaseEntry OBJECT-TYPE
			SYNTAX StpExtPortBaseEntry
			MAX-ACCESS not-accessible
			STATUS current
			DESCRIPTION
				"Description."
			INDEX { stpExtPortBaseDeviceIndex, stpExtPortBaseCardIndex, stpExtPortBasePortIndex }
			::= { stpExtPortBaseTable 1 }

		
		StpExtPortBaseEntry ::=
			SEQUENCE { 
				stpExtPortBaseDeviceIndex
					NscrtvPonExtDeviceIndex,
				stpExtPortBaseCardIndex
					NscrtvPonExtCardIndex,
				stpExtPortBasePortIndex
					NscrtvPonPortIndex,
				stpExtPortBaseEnable
					INTEGER,
				stpExtPortBaseEdged
					INTEGER,
				stpExtPortBaseAutoEdged
					INTEGER,
				stpExtPortBaseP2P
					INTEGER,
				stpExtPortBaseBpduGuard
					INTEGER,
				stpExtPortBaseMcheck
					INTEGER,
				stpExtPortBaseRestrictedRole
					INTEGER,
				stpExtPortBaseRestrictedTcn
					INTEGER
			 }

		-- 1.3.6.1.4.1.34592.1.3.100.20.4.1.1
		stpExtPortBaseDeviceIndex OBJECT-TYPE
			SYNTAX NscrtvPonExtDeviceIndex
			MAX-ACCESS not-accessible
			STATUS current
			DESCRIPTION
				"Description."
			::= { stpExtPortBaseEntry 1 }

		
		-- 1.3.6.1.4.1.34592.1.3.100.20.4.1.2
		stpExtPortBaseCardIndex OBJECT-TYPE
			SYNTAX NscrtvPonExtCardIndex
			MAX-ACCESS not-accessible
			STATUS current
			DESCRIPTION
				"Description."
			::= { stpExtPortBaseEntry 2 }

		
		-- 1.3.6.1.4.1.34592.1.3.100.20.4.1.3
		stpExtPortBasePortIndex OBJECT-TYPE
			SYNTAX NscrtvPonPortIndex
			MAX-ACCESS not-accessible
			STATUS current
			DESCRIPTION
				"Description."
			::= { stpExtPortBaseEntry 3 }

		
		-- 1.3.6.1.4.1.34592.1.3.100.20.4.1.4
		stpExtPortBaseEnable OBJECT-TYPE
			SYNTAX INTEGER
				{
				disable(0),
				enable(1)
				}
			MAX-ACCESS read-write
			STATUS current
			DESCRIPTION
				"Description."
			::= { stpExtPortBaseEntry 4 }

		
		-- 1.3.6.1.4.1.34592.1.3.100.20.4.1.5
		stpExtPortBaseEdged OBJECT-TYPE
			SYNTAX INTEGER
				{
				disable(0),
				enable(1)
				}
			MAX-ACCESS read-write
			STATUS current
			DESCRIPTION
				"Description."
			::= { stpExtPortBaseEntry 5 }

		
		-- 1.3.6.1.4.1.34592.1.3.100.20.4.1.6
		stpExtPortBaseAutoEdged OBJECT-TYPE
			SYNTAX INTEGER
				{
				disable(0),
				enable(1)
				}
			MAX-ACCESS read-write
			STATUS current
			DESCRIPTION
				"Description."
			::= { stpExtPortBaseEntry 6 }

		
		-- 1.3.6.1.4.1.34592.1.3.100.20.4.1.7
		stpExtPortBaseP2P OBJECT-TYPE
			SYNTAX INTEGER
				{
				true(0),
				false(1),
				auto(2)
				}
			MAX-ACCESS read-write
			STATUS current
			DESCRIPTION
				"Description."
			::= { stpExtPortBaseEntry 7 }

		
		-- 1.3.6.1.4.1.34592.1.3.100.20.4.1.8
		stpExtPortBaseBpduGuard OBJECT-TYPE
			SYNTAX INTEGER
				{
				disable(0),
				enable(1)
				}
			MAX-ACCESS read-write
			STATUS current
			DESCRIPTION
				"Description."
			::= { stpExtPortBaseEntry 8 }

		
		-- 1.3.6.1.4.1.34592.1.3.100.20.4.1.9
		stpExtPortBaseMcheck OBJECT-TYPE
			SYNTAX INTEGER
				{
				none(0),
				action(1)
				}
			MAX-ACCESS read-write
			STATUS current
			DESCRIPTION
				"Description."
			::= { stpExtPortBaseEntry 9 }

		
		-- 1.3.6.1.4.1.34592.1.3.100.20.4.1.10
		stpExtPortBaseRestrictedRole OBJECT-TYPE
			SYNTAX INTEGER
				{
				disable(0),
				enable(1)
				}
			MAX-ACCESS read-write
			STATUS current
			DESCRIPTION
				"Description."
			::= { stpExtPortBaseEntry 10 }

		
		-- 1.3.6.1.4.1.34592.1.3.100.20.4.1.11
		stpExtPortBaseRestrictedTcn OBJECT-TYPE
			SYNTAX INTEGER
				{
				disable(0),
				enable(1)
				}
			MAX-ACCESS read-write
			STATUS current
			DESCRIPTION
				"Description."
			::= { stpExtPortBaseEntry 11 }

		
		-- 1.3.6.1.4.1.34592.1.3.100.20.5
		stpExtPortInstanceTable OBJECT-TYPE
			SYNTAX SEQUENCE OF StpExtPortInstanceEntry
			MAX-ACCESS not-accessible
			STATUS current
			DESCRIPTION
				"Description."
			::= { stpExtManagementObjects 5 }

		
		-- 1.3.6.1.4.1.34592.1.3.100.20.5.1
		stpExtPortInstanceEntry OBJECT-TYPE
			SYNTAX StpExtPortInstanceEntry
			MAX-ACCESS not-accessible
			STATUS current
			DESCRIPTION
				"Description."
			INDEX { stpExtPortInstanceDeviceIndex, stpExtPortInstanceCardIndex, stpExtPortInstancePortIndex, stpExtPortInstanceIndex }
			::= { stpExtPortInstanceTable 1 }

		
		StpExtPortInstanceEntry ::=
			SEQUENCE { 
				stpExtPortInstanceDeviceIndex
					NscrtvPonExtDeviceIndex,
				stpExtPortInstanceCardIndex
					NscrtvPonExtCardIndex,
				stpExtPortInstancePortIndex
					NscrtvPonPortIndex,
				stpExtPortInstanceIndex
					Unsigned32,
				stpExtPortInstancePriority
					Unsigned32,
				stpExtPortInstancePathCost
					Unsigned32
			 }

		-- 1.3.6.1.4.1.34592.1.3.100.20.5.1.1
		stpExtPortInstanceDeviceIndex OBJECT-TYPE
			SYNTAX NscrtvPonExtDeviceIndex
			MAX-ACCESS not-accessible
			STATUS current
			DESCRIPTION
				"Description."
			::= { stpExtPortInstanceEntry 1 }

		
		-- 1.3.6.1.4.1.34592.1.3.100.20.5.1.2
		stpExtPortInstanceCardIndex OBJECT-TYPE
			SYNTAX NscrtvPonExtCardIndex
			MAX-ACCESS not-accessible
			STATUS current
			DESCRIPTION
				"Description."
			::= { stpExtPortInstanceEntry 2 }

		
		-- 1.3.6.1.4.1.34592.1.3.100.20.5.1.3
		stpExtPortInstancePortIndex OBJECT-TYPE
			SYNTAX NscrtvPonPortIndex
			MAX-ACCESS not-accessible
			STATUS current
			DESCRIPTION
				"Description."
			::= { stpExtPortInstanceEntry 3 }

		
		-- 1.3.6.1.4.1.34592.1.3.100.20.5.1.4
		stpExtPortInstanceIndex OBJECT-TYPE
			SYNTAX Unsigned32 (0..7)
			MAX-ACCESS not-accessible
			STATUS current
			DESCRIPTION
				"Description."
			::= { stpExtPortInstanceEntry 4 }

		
		-- 1.3.6.1.4.1.34592.1.3.100.20.5.1.5
		stpExtPortInstancePriority OBJECT-TYPE
			SYNTAX Unsigned32 (0..255)
			MAX-ACCESS read-write
			STATUS current
			DESCRIPTION
				"Description."
			::= { stpExtPortInstanceEntry 5 }

		
		-- 1.3.6.1.4.1.34592.1.3.100.20.5.1.6
		stpExtPortInstancePathCost OBJECT-TYPE
			SYNTAX Unsigned32 (0..200000000)
			MAX-ACCESS read-write
			STATUS current
			DESCRIPTION
				"Description."
			::= { stpExtPortInstanceEntry 6 }

		
		-- 1.3.6.1.4.1.34592.1.3.100.20.6
		stpExtGlobalStateTable OBJECT-TYPE
			SYNTAX SEQUENCE OF StpExtGlobalStateEntry
			MAX-ACCESS not-accessible
			STATUS current
			DESCRIPTION
				"Description."
			::= { stpExtManagementObjects 6 }

		
		-- 1.3.6.1.4.1.34592.1.3.100.20.6.1
		stpExtGlobalStateEntry OBJECT-TYPE
			SYNTAX StpExtGlobalStateEntry
			MAX-ACCESS not-accessible
			STATUS current
			DESCRIPTION
				"Description."
			INDEX { stpExtGlobalStateDeviceIndex }
			::= { stpExtGlobalStateTable 1 }

		
		StpExtGlobalStateEntry ::=
			SEQUENCE { 
				stpExtGlobalStateDeviceIndex
					NscrtvPonExtDeviceIndex,
				stpExtGlobalStateRoot
					DisplayString,
				stpExtGlobalStateRootCost
					Unsigned32,
				stpExtGlobalStateRootForwardDelay
					Unsigned32,
				stpExtGlobalStateRootMaxAge
					Unsigned32
			 }

		-- 1.3.6.1.4.1.34592.1.3.100.20.6.1.1
		stpExtGlobalStateDeviceIndex OBJECT-TYPE
			SYNTAX NscrtvPonExtDeviceIndex
			MAX-ACCESS not-accessible
			STATUS current
			DESCRIPTION
				"Description."
			::= { stpExtGlobalStateEntry 1 }

		
		-- 1.3.6.1.4.1.34592.1.3.100.20.6.1.2
		stpExtGlobalStateRoot OBJECT-TYPE
			SYNTAX DisplayString
			MAX-ACCESS read-only
			STATUS current
			DESCRIPTION
				"Description."
			::= { stpExtGlobalStateEntry 2 }

		
		-- 1.3.6.1.4.1.34592.1.3.100.20.6.1.3
		stpExtGlobalStateRootCost OBJECT-TYPE
			SYNTAX Unsigned32
			MAX-ACCESS read-only
			STATUS current
			DESCRIPTION
				"Description."
			::= { stpExtGlobalStateEntry 3 }

		
		-- 1.3.6.1.4.1.34592.1.3.100.20.6.1.4
		stpExtGlobalStateRootForwardDelay OBJECT-TYPE
			SYNTAX Unsigned32
			MAX-ACCESS read-only
			STATUS current
			DESCRIPTION
				"Description."
			::= { stpExtGlobalStateEntry 4 }

		
		-- 1.3.6.1.4.1.34592.1.3.100.20.6.1.5
		stpExtGlobalStateRootMaxAge OBJECT-TYPE
			SYNTAX Unsigned32
			MAX-ACCESS read-only
			STATUS current
			DESCRIPTION
				"Description."
			::= { stpExtGlobalStateEntry 5 }

		
		-- 1.3.6.1.4.1.34592.1.3.100.20.7
		stpExtInstanceStateTable OBJECT-TYPE
			SYNTAX SEQUENCE OF StpExtInstanceStateEntry
			MAX-ACCESS not-accessible
			STATUS current
			DESCRIPTION
				"Description."
			::= { stpExtManagementObjects 7 }

		
		-- 1.3.6.1.4.1.34592.1.3.100.20.7.1
		stpExtInstanceStateEntry OBJECT-TYPE
			SYNTAX StpExtInstanceStateEntry
			MAX-ACCESS not-accessible
			STATUS current
			DESCRIPTION
				"Description."
			INDEX { stpExtInstanceStateInstanceIndex }
			::= { stpExtInstanceStateTable 1 }

		
		StpExtInstanceStateEntry ::=
			SEQUENCE { 
				stpExtInstanceStateInstanceIndex
					Unsigned32,
				stpExtInstanceStateRegionRoot
					DisplayString,
				stpExtInstanceStateRegionRootCost
					Unsigned32,
				stpExtInstanceStateRegionRootForwardDelay
					Unsigned32,
				stpExtInstanceStateRegionRootMaxAge
					Unsigned32
			 }

		-- 1.3.6.1.4.1.34592.1.3.100.20.7.1.1
		stpExtInstanceStateInstanceIndex OBJECT-TYPE
			SYNTAX Unsigned32
			MAX-ACCESS not-accessible
			STATUS current
			DESCRIPTION
				"Description."
			::= { stpExtInstanceStateEntry 1 }

		
		-- 1.3.6.1.4.1.34592.1.3.100.20.7.1.2
		stpExtInstanceStateRegionRoot OBJECT-TYPE
			SYNTAX DisplayString
			MAX-ACCESS read-only
			STATUS current
			DESCRIPTION
				"Description."
			::= { stpExtInstanceStateEntry 2 }

		
		-- 1.3.6.1.4.1.34592.1.3.100.20.7.1.3
		stpExtInstanceStateRegionRootCost OBJECT-TYPE
			SYNTAX Unsigned32
			MAX-ACCESS read-only
			STATUS current
			DESCRIPTION
				"Description."
			::= { stpExtInstanceStateEntry 3 }

		
		-- 1.3.6.1.4.1.34592.1.3.100.20.7.1.4
		stpExtInstanceStateRegionRootForwardDelay OBJECT-TYPE
			SYNTAX Unsigned32
			MAX-ACCESS read-only
			STATUS current
			DESCRIPTION
				"Description."
			::= { stpExtInstanceStateEntry 4 }

		
		-- 1.3.6.1.4.1.34592.1.3.100.20.7.1.5
		stpExtInstanceStateRegionRootMaxAge OBJECT-TYPE
			SYNTAX Unsigned32
			MAX-ACCESS read-only
			STATUS current
			DESCRIPTION
				"Description."
			::= { stpExtInstanceStateEntry 5 }

		
		-- 1.3.6.1.4.1.34592.1.3.100.20.8
		stpExtPortStateTable OBJECT-TYPE
			SYNTAX SEQUENCE OF StpExtPortStateEntry
			MAX-ACCESS not-accessible
			STATUS current
			DESCRIPTION
				"Description."
			::= { stpExtManagementObjects 8 }

		
		-- 1.3.6.1.4.1.34592.1.3.100.20.8.1
		stpExtPortStateEntry OBJECT-TYPE
			SYNTAX StpExtPortStateEntry
			MAX-ACCESS not-accessible
			STATUS current
			DESCRIPTION
				"Description."
			INDEX { stpExtPortStateDeviceIndex, stpExtPortStatePortIndex, stpExtPortStateCardIndex }
			::= { stpExtPortStateTable 1 }

		
		StpExtPortStateEntry ::=
			SEQUENCE { 
				stpExtPortStateDeviceIndex
					NscrtvPonExtDeviceIndex,
				stpExtPortStateCardIndex
					NscrtvPonExtCardIndex,
				stpExtPortStatePortIndex
					NscrtvPonPortIndex,
				stpExtPortStateDesignateBridge
					DisplayString,
				stpExtPortStateDesignatePort
					DisplayString,
				stpExtPortStateOperP2P
					INTEGER,
				stpExtPortStateOperEdgedPort
					INTEGER,
				stpExtPortStatePortMode
					INTEGER,
				stpExtPortStateHelloTime
					Unsigned32,
				stpExtPortStateMaxAge
					Unsigned32,
				stpExtPortStateForwardDelay
					Unsigned32,
				stpExtPortStateMessageAge
					Unsigned32,
				stpExtPortStateRemainHops
					Unsigned32,
				stpExtPortStateBpduSentSum
					Unsigned32,
				stpExtPortStateBpduSentTcn
					Unsigned32,
				stpExtPortStateBpduSentStp
					Unsigned32,
				stpExtPortStateBpduSentRst
					Unsigned32,
				stpExtPortStateBpduSentMst
					Unsigned32,
				stpExtPortStateBpduRecvSum
					Unsigned32,
				stpExtPortStateBpduRecvTcn
					Unsigned32,
				stpExtPortStateBpduRecvStp
					Unsigned32,
				stpExtPortStateBpduRecvRstp
					Unsigned32,
				stpExtPortStateBpduRecvMst
					Unsigned32
			 }

		-- 1.3.6.1.4.1.34592.1.3.100.20.8.1.1
		stpExtPortStateDeviceIndex OBJECT-TYPE
			SYNTAX NscrtvPonExtDeviceIndex
			MAX-ACCESS not-accessible
			STATUS current
			DESCRIPTION
				"Description."
			::= { stpExtPortStateEntry 1 }

		
		-- 1.3.6.1.4.1.34592.1.3.100.20.8.1.2
		stpExtPortStateCardIndex OBJECT-TYPE
			SYNTAX NscrtvPonExtCardIndex
			MAX-ACCESS not-accessible
			STATUS current
			DESCRIPTION
				"Description."
			::= { stpExtPortStateEntry 2 }

		
		-- 1.3.6.1.4.1.34592.1.3.100.20.8.1.3
		stpExtPortStatePortIndex OBJECT-TYPE
			SYNTAX NscrtvPonPortIndex
			MAX-ACCESS not-accessible
			STATUS current
			DESCRIPTION
				"Description."
			::= { stpExtPortStateEntry 3 }

		
		-- 1.3.6.1.4.1.34592.1.3.100.20.8.1.4
		stpExtPortStateDesignateBridge OBJECT-TYPE
			SYNTAX DisplayString
			MAX-ACCESS read-only
			STATUS current
			DESCRIPTION
				"Description."
			::= { stpExtPortStateEntry 4 }

		
		-- 1.3.6.1.4.1.34592.1.3.100.20.8.1.5
		stpExtPortStateDesignatePort OBJECT-TYPE
			SYNTAX DisplayString
			MAX-ACCESS read-only
			STATUS current
			DESCRIPTION
				"Description."
			::= { stpExtPortStateEntry 5 }

		
		-- 1.3.6.1.4.1.34592.1.3.100.20.8.1.6
		stpExtPortStateOperP2P OBJECT-TYPE
			SYNTAX INTEGER
				{
				false(0),
				true(1)
				}
			MAX-ACCESS read-only
			STATUS current
			DESCRIPTION
				"Description."
			::= { stpExtPortStateEntry 6 }

		
		-- 1.3.6.1.4.1.34592.1.3.100.20.8.1.7
		stpExtPortStateOperEdgedPort OBJECT-TYPE
			SYNTAX INTEGER
				{
				false(0),
				true(1)
				}
			MAX-ACCESS read-only
			STATUS current
			DESCRIPTION
				"Description."
			::= { stpExtPortStateEntry 7 }

		
		-- 1.3.6.1.4.1.34592.1.3.100.20.8.1.8
		stpExtPortStatePortMode OBJECT-TYPE
			SYNTAX INTEGER
				{
				stp(0),
				rstp(2),
				mstp(3)
				}
			MAX-ACCESS read-only
			STATUS current
			DESCRIPTION
				"Description."
			::= { stpExtPortStateEntry 8 }

		
		-- 1.3.6.1.4.1.34592.1.3.100.20.8.1.9
		stpExtPortStateHelloTime OBJECT-TYPE
			SYNTAX Unsigned32
			MAX-ACCESS read-only
			STATUS current
			DESCRIPTION
				"Description."
			::= { stpExtPortStateEntry 9 }

		
		-- 1.3.6.1.4.1.34592.1.3.100.20.8.1.10
		stpExtPortStateMaxAge OBJECT-TYPE
			SYNTAX Unsigned32
			MAX-ACCESS read-only
			STATUS current
			DESCRIPTION
				"Description."
			::= { stpExtPortStateEntry 10 }

		
		-- 1.3.6.1.4.1.34592.1.3.100.20.8.1.11
		stpExtPortStateForwardDelay OBJECT-TYPE
			SYNTAX Unsigned32
			MAX-ACCESS read-only
			STATUS current
			DESCRIPTION
				"Description."
			::= { stpExtPortStateEntry 11 }

		
		-- 1.3.6.1.4.1.34592.1.3.100.20.8.1.12
		stpExtPortStateMessageAge OBJECT-TYPE
			SYNTAX Unsigned32
			MAX-ACCESS read-only
			STATUS current
			DESCRIPTION
				"Description."
			::= { stpExtPortStateEntry 12 }

		
		-- 1.3.6.1.4.1.34592.1.3.100.20.8.1.13
		stpExtPortStateRemainHops OBJECT-TYPE
			SYNTAX Unsigned32
			MAX-ACCESS read-only
			STATUS current
			DESCRIPTION
				"Description."
			::= { stpExtPortStateEntry 13 }

		
		-- 1.3.6.1.4.1.34592.1.3.100.20.8.1.14
		stpExtPortStateBpduSentSum OBJECT-TYPE
			SYNTAX Unsigned32
			MAX-ACCESS read-only
			STATUS current
			DESCRIPTION
				"Description."
			::= { stpExtPortStateEntry 14 }

		
		-- 1.3.6.1.4.1.34592.1.3.100.20.8.1.15
		stpExtPortStateBpduSentTcn OBJECT-TYPE
			SYNTAX Unsigned32
			MAX-ACCESS read-only
			STATUS current
			DESCRIPTION
				"Description."
			::= { stpExtPortStateEntry 15 }

		
		-- 1.3.6.1.4.1.34592.1.3.100.20.8.1.16
		stpExtPortStateBpduSentStp OBJECT-TYPE
			SYNTAX Unsigned32
			MAX-ACCESS read-only
			STATUS current
			DESCRIPTION
				"Description."
			::= { stpExtPortStateEntry 16 }

		
		-- 1.3.6.1.4.1.34592.1.3.100.20.8.1.17
		stpExtPortStateBpduSentRst OBJECT-TYPE
			SYNTAX Unsigned32
			MAX-ACCESS read-only
			STATUS current
			DESCRIPTION
				"Description."
			::= { stpExtPortStateEntry 17 }

		
		-- 1.3.6.1.4.1.34592.1.3.100.20.8.1.18
		stpExtPortStateBpduSentMst OBJECT-TYPE
			SYNTAX Unsigned32
			MAX-ACCESS read-only
			STATUS current
			DESCRIPTION
				"Description."
			::= { stpExtPortStateEntry 18 }

		
		-- 1.3.6.1.4.1.34592.1.3.100.20.8.1.19
		stpExtPortStateBpduRecvSum OBJECT-TYPE
			SYNTAX Unsigned32
			MAX-ACCESS read-only
			STATUS current
			DESCRIPTION
				"Description."
			::= { stpExtPortStateEntry 19 }

		
		-- 1.3.6.1.4.1.34592.1.3.100.20.8.1.20
		stpExtPortStateBpduRecvTcn OBJECT-TYPE
			SYNTAX Unsigned32
			MAX-ACCESS read-only
			STATUS current
			DESCRIPTION
				"Description."
			::= { stpExtPortStateEntry 20 }

		
		-- 1.3.6.1.4.1.34592.1.3.100.20.8.1.21
		stpExtPortStateBpduRecvStp OBJECT-TYPE
			SYNTAX Unsigned32
			MAX-ACCESS read-only
			STATUS current
			DESCRIPTION
				"Description."
			::= { stpExtPortStateEntry 21 }

		
		-- 1.3.6.1.4.1.34592.1.3.100.20.8.1.22
		stpExtPortStateBpduRecvRstp OBJECT-TYPE
			SYNTAX Unsigned32
			MAX-ACCESS read-only
			STATUS current
			DESCRIPTION
				"Description."
			::= { stpExtPortStateEntry 22 }

		
		-- 1.3.6.1.4.1.34592.1.3.100.20.8.1.23
		stpExtPortStateBpduRecvMst OBJECT-TYPE
			SYNTAX Unsigned32
			MAX-ACCESS read-only
			STATUS current
			DESCRIPTION
				"Description."
			::= { stpExtPortStateEntry 23 }

		
		-- 1.3.6.1.4.1.34592.1.3.100.20.9
		stpExtPortInstanceStateTable OBJECT-TYPE
			SYNTAX SEQUENCE OF StpExtPortInstanceStateEntry
			MAX-ACCESS not-accessible
			STATUS current
			DESCRIPTION
				"Description."
			::= { stpExtManagementObjects 9 }

		
		-- 1.3.6.1.4.1.34592.1.3.100.20.9.1
		stpExtPortInstanceStateEntry OBJECT-TYPE
			SYNTAX StpExtPortInstanceStateEntry
			MAX-ACCESS not-accessible
			STATUS current
			DESCRIPTION
				"Description."
			INDEX { stpExtPortInstanceStateDeviceIndex, stpExtPortInstanceStateCardIndex, stpExtPortInstanceStatePortIndex, stpExtPortInstanceStateInstanceIndex }
			::= { stpExtPortInstanceStateTable 1 }

		
		StpExtPortInstanceStateEntry ::=
			SEQUENCE { 
				stpExtPortInstanceStateDeviceIndex
					NscrtvPonExtDeviceIndex,
				stpExtPortInstanceStateCardIndex
					NscrtvPonExtCardIndex,
				stpExtPortInstanceStatePortIndex
					NscrtvPonPortIndex,
				stpExtPortInstanceStateInstanceIndex
					Unsigned32,
				stpExtPortInstanceStatePortRole
					DisplayString,
				stpExtPortInstanceStatePortState
					DisplayString,
				stpExtPortInstanceStatePathCost
					Unsigned32
			 }

		-- 1.3.6.1.4.1.34592.1.3.100.20.9.1.1
		stpExtPortInstanceStateDeviceIndex OBJECT-TYPE
			SYNTAX NscrtvPonExtDeviceIndex
			MAX-ACCESS not-accessible
			STATUS current
			DESCRIPTION
				"Description."
			::= { stpExtPortInstanceStateEntry 1 }

		
		-- 1.3.6.1.4.1.34592.1.3.100.20.9.1.2
		stpExtPortInstanceStateCardIndex OBJECT-TYPE
			SYNTAX NscrtvPonExtCardIndex
			MAX-ACCESS not-accessible
			STATUS current
			DESCRIPTION
				"Description."
			::= { stpExtPortInstanceStateEntry 2 }

		
		-- 1.3.6.1.4.1.34592.1.3.100.20.9.1.3
		stpExtPortInstanceStatePortIndex OBJECT-TYPE
			SYNTAX NscrtvPonPortIndex
			MAX-ACCESS not-accessible
			STATUS current
			DESCRIPTION
				"Description."
			::= { stpExtPortInstanceStateEntry 3 }

		
		-- 1.3.6.1.4.1.34592.1.3.100.20.9.1.4
		stpExtPortInstanceStateInstanceIndex OBJECT-TYPE
			SYNTAX Unsigned32
			MAX-ACCESS not-accessible
			STATUS current
			DESCRIPTION
				"Description."
			::= { stpExtPortInstanceStateEntry 4 }

		
		-- 1.3.6.1.4.1.34592.1.3.100.20.9.1.5
		stpExtPortInstanceStatePortRole OBJECT-TYPE
			SYNTAX DisplayString
			MAX-ACCESS read-only
			STATUS current
			DESCRIPTION
				"Description."
			::= { stpExtPortInstanceStateEntry 5 }

		
		-- 1.3.6.1.4.1.34592.1.3.100.20.9.1.6
		stpExtPortInstanceStatePortState OBJECT-TYPE
			SYNTAX DisplayString
			MAX-ACCESS read-only
			STATUS current
			DESCRIPTION
				"Description."
			::= { stpExtPortInstanceStateEntry 6 }

		
		-- 1.3.6.1.4.1.34592.1.3.100.20.9.1.7
		stpExtPortInstanceStatePathCost OBJECT-TYPE
			SYNTAX Unsigned32
			MAX-ACCESS read-only
			STATUS current
			DESCRIPTION
				"Description."
			::= { stpExtPortInstanceStateEntry 7 }

		
		-- 1.3.6.1.4.1.34592.1.3.100.21
		statisticsExtObject OBJECT IDENTIFIER ::= { nscrtvPonTreeExt 21 }

		
		-- 1.3.6.1.4.1.34592.1.3.100.21.1
		curStatsExtTable OBJECT-TYPE
			SYNTAX SEQUENCE OF CurStatsExtEntry
			MAX-ACCESS not-accessible
			STATUS current
			DESCRIPTION
				"Description."
			::= { statisticsExtObject 1 }

		
		-- 1.3.6.1.4.1.34592.1.3.100.21.1.1
		curStatsExtEntry OBJECT-TYPE
			SYNTAX CurStatsExtEntry
			MAX-ACCESS not-accessible
			STATUS current
			DESCRIPTION
				"Description."
			INDEX { curStatsExtDeviceIndex, curStatsExtCardIndex, curStatsExtPortIndex }
			::= { curStatsExtTable 1 }

		
		CurStatsExtEntry ::=
			SEQUENCE { 
				curStatsExtDeviceIndex
					Integer32,
				curStatsExtCardIndex
					Integer32,
				curStatsExtPortIndex
					Integer32,
				curStatsExtRxRate
					Counter64,
				curStatsExtTxRate
					Counter64
			 }

		-- 1.3.6.1.4.1.34592.1.3.100.21.1.1.1
		curStatsExtDeviceIndex OBJECT-TYPE
			SYNTAX Integer32
			MAX-ACCESS read-only
			STATUS current
			DESCRIPTION
				"Description."
			::= { curStatsExtEntry 1 }

		
		-- 1.3.6.1.4.1.34592.1.3.100.21.1.1.2
		curStatsExtCardIndex OBJECT-TYPE
			SYNTAX Integer32
			MAX-ACCESS read-only
			STATUS current
			DESCRIPTION
				"Description."
			::= { curStatsExtEntry 2 }

		
		-- 1.3.6.1.4.1.34592.1.3.100.21.1.1.3
		curStatsExtPortIndex OBJECT-TYPE
			SYNTAX Integer32
			MAX-ACCESS read-only
			STATUS current
			DESCRIPTION
				"Description."
			::= { curStatsExtEntry 3 }

		
		-- 1.3.6.1.4.1.34592.1.3.100.21.1.1.4
		curStatsExtRxRate OBJECT-TYPE
			SYNTAX Counter64
			MAX-ACCESS read-only
			STATUS current
			DESCRIPTION
				"Description."
			::= { curStatsExtEntry 4 }

		
		-- 1.3.6.1.4.1.34592.1.3.100.21.1.1.5
		curStatsExtTxRate OBJECT-TYPE
			SYNTAX Counter64
			MAX-ACCESS read-only
			STATUS current
			DESCRIPTION
				"Description."
			::= { curStatsExtEntry 5 }

		
		-- 1.3.6.1.4.1.34592.1.3.100.22
		qosManagementExtObjects OBJECT IDENTIFIER ::= { nscrtvPonTreeExt 22 }

		
		-- 1.3.6.1.4.1.34592.1.3.100.22.1
		deviceBaseQosMapExtTable OBJECT-TYPE
			SYNTAX SEQUENCE OF DeviceBaseQosMapExtEntry
			MAX-ACCESS not-accessible
			STATUS current
			DESCRIPTION
				"Description."
			::= { qosManagementExtObjects 1 }

		
		-- 1.3.6.1.4.1.34592.1.3.100.22.1.1
		deviceBaseQosMapExtEntry OBJECT-TYPE
			SYNTAX DeviceBaseQosMapExtEntry
			MAX-ACCESS not-accessible
			STATUS current
			DESCRIPTION
				"Description."
			INDEX { deviceBaseQosMapExtDeviceIndex, deviceBaseQosMapExtRuleIndex }
			::= { deviceBaseQosMapExtTable 1 }

		
		DeviceBaseQosMapExtEntry ::=
			SEQUENCE { 
				deviceBaseQosMapExtDeviceIndex
					Unsigned32,
				deviceBaseQosMapExtRuleIndex
					INTEGER,
				deviceBaseQosMapExtOctet
					OCTET STRING
			 }

		-- 1.3.6.1.4.1.34592.1.3.100.22.1.1.1
		deviceBaseQosMapExtDeviceIndex OBJECT-TYPE
			SYNTAX Unsigned32
			MAX-ACCESS not-accessible
			STATUS current
			DESCRIPTION
				"Description."
			::= { deviceBaseQosMapExtEntry 1 }

		
		-- 1.3.6.1.4.1.34592.1.3.100.22.1.1.2
		deviceBaseQosMapExtRuleIndex OBJECT-TYPE
			SYNTAX INTEGER { color(1) }
			MAX-ACCESS not-accessible
			STATUS current
			DESCRIPTION
				"Description."
			::= { deviceBaseQosMapExtEntry 2 }

		
		-- 1.3.6.1.4.1.34592.1.3.100.22.1.1.3
		deviceBaseQosMapExtOctet OBJECT-TYPE
			SYNTAX OCTET STRING (SIZE (8..64))
			MAX-ACCESS read-write
			STATUS current
			DESCRIPTION
				"Description."
			::= { deviceBaseQosMapExtEntry 3 }

		
		-- 1.3.6.1.4.1.34592.1.3.100.22.2
		portBaseQosMapExtTable OBJECT-TYPE
			SYNTAX SEQUENCE OF PortBaseQosMapExtEntry
			MAX-ACCESS not-accessible
			STATUS current
			DESCRIPTION
				"Description."
			::= { qosManagementExtObjects 2 }

		
		-- 1.3.6.1.4.1.34592.1.3.100.22.2.1
		portBaseQosMapExtEntry OBJECT-TYPE
			SYNTAX PortBaseQosMapExtEntry
			MAX-ACCESS not-accessible
			STATUS current
			DESCRIPTION
				"Description."
			INDEX { portBaseQosMapExtDeviceIndex, portBaseQosMapExtCardIndex, portBaseQosMapExtPortIndex, portBaseQosMapExtRuleIndex }
			::= { portBaseQosMapExtTable 1 }

		
		PortBaseQosMapExtEntry ::=
			SEQUENCE { 
				portBaseQosMapExtDeviceIndex
					Unsigned32,
				portBaseQosMapExtCardIndex
					INTEGER,
				portBaseQosMapExtPortIndex
					INTEGER,
				portBaseQosMapExtRuleIndex
					INTEGER,
				portBaseQosMapExtOctet
					OCTET STRING
			 }

		-- 1.3.6.1.4.1.34592.1.3.100.22.2.1.1
		portBaseQosMapExtDeviceIndex OBJECT-TYPE
			SYNTAX Unsigned32
			MAX-ACCESS read-write
			STATUS current
			DESCRIPTION
				"Description."
			::= { portBaseQosMapExtEntry 1 }

		
		-- 1.3.6.1.4.1.34592.1.3.100.22.2.1.2
		portBaseQosMapExtCardIndex OBJECT-TYPE
			SYNTAX INTEGER (0..255)
			MAX-ACCESS not-accessible
			STATUS current
			DESCRIPTION
				"Description."
			::= { portBaseQosMapExtEntry 2 }

		
		-- 1.3.6.1.4.1.34592.1.3.100.22.2.1.3
		portBaseQosMapExtPortIndex OBJECT-TYPE
			SYNTAX INTEGER (0..255)
			MAX-ACCESS not-accessible
			STATUS current
			DESCRIPTION
				"Description."
			::= { portBaseQosMapExtEntry 3 }

		
		-- 1.3.6.1.4.1.34592.1.3.100.22.2.1.4
		portBaseQosMapExtRuleIndex OBJECT-TYPE
			SYNTAX INTEGER { color(1) }
			MAX-ACCESS not-accessible
			STATUS current
			DESCRIPTION
				"Description."
			::= { portBaseQosMapExtEntry 4 }

		
		-- 1.3.6.1.4.1.34592.1.3.100.22.2.1.5
		portBaseQosMapExtOctet OBJECT-TYPE
			SYNTAX OCTET STRING (SIZE (8..64))
			MAX-ACCESS read-write
			STATUS current
			DESCRIPTION
				"Description."
			::= { portBaseQosMapExtEntry 5 }

		
		-- 1.3.6.1.4.1.34592.1.3.100.23
		eponOnuWifiWanExtObjects OBJECT IDENTIFIER ::= { nscrtvPonTreeExt 23 }

		
		-- 1.3.6.1.4.1.34592.1.3.100.23.1
		eponOnuWifiWanExtTable OBJECT-TYPE
			SYNTAX SEQUENCE OF EponOnuWifiWanExtEntry
			MAX-ACCESS not-accessible
			STATUS current
			DESCRIPTION
				"Description."
			::= { eponOnuWifiWanExtObjects 1 }

		
		-- 1.3.6.1.4.1.34592.1.3.100.23.1.1
		eponOnuWifiWanExtEntry OBJECT-TYPE
			SYNTAX EponOnuWifiWanExtEntry
			MAX-ACCESS not-accessible
			STATUS current
			DESCRIPTION
				"Description."
			INDEX { eponOnuWifiWanExtOnuIndex, eponOnuWifiWanExtWanIndex }
			::= { eponOnuWifiWanExtTable 1 }

		
		EponOnuWifiWanExtEntry ::=
			SEQUENCE { 
				eponOnuWifiWanExtOnuIndex
					EponDeviceIndex,
				eponOnuWifiWanExtWanIndex
					Integer32,
				eponOnuWifiWanExtWanName
					OCTET STRING,
				eponOnuWifiWanExtSrvName
					OCTET STRING
			 }

		-- 1.3.6.1.4.1.34592.1.3.100.23.1.1.1
		eponOnuWifiWanExtOnuIndex OBJECT-TYPE
			SYNTAX EponDeviceIndex
			MAX-ACCESS not-accessible
			STATUS current
			DESCRIPTION
				"Description."
			::= { eponOnuWifiWanExtEntry 1 }

		
		-- 1.3.6.1.4.1.34592.1.3.100.23.1.1.2
		eponOnuWifiWanExtWanIndex OBJECT-TYPE
			SYNTAX Integer32 (1..8)
			MAX-ACCESS not-accessible
			STATUS current
			DESCRIPTION
				"Description."
			::= { eponOnuWifiWanExtEntry 2 }

		
		-- 1.3.6.1.4.1.34592.1.3.100.23.1.1.3
		eponOnuWifiWanExtWanName OBJECT-TYPE
			SYNTAX OCTET STRING (SIZE (0..32))
			MAX-ACCESS read-write
			STATUS current
			DESCRIPTION
				"Description."
			::= { eponOnuWifiWanExtEntry 3 }

		
		-- 1.3.6.1.4.1.34592.1.3.100.23.1.1.4
		eponOnuWifiWanExtSrvName OBJECT-TYPE
			SYNTAX OCTET STRING (SIZE (0..64))
			MAX-ACCESS read-write
			STATUS current
			DESCRIPTION
				"Description."
			::= { eponOnuWifiWanExtEntry 4 }

		
		-- 1.3.6.1.4.1.34592.1.3.100.24
		lldpObjects OBJECT IDENTIFIER ::= { nscrtvPonTreeExt 24 }

		
		-- 1.3.6.1.4.1.34592.1.3.100.24.1
		lldpXdot3RemPortNeighborsTable OBJECT-TYPE
			SYNTAX SEQUENCE OF LldpXdot3RemPortNeighborsEntry
			MAX-ACCESS not-accessible
			STATUS current
			DESCRIPTION
				"Description."
			::= { lldpObjects 1 }

		
		-- 1.3.6.1.4.1.34592.1.3.100.24.1.1
		lldpXdot3RemPortNeighborsEntry OBJECT-TYPE
			SYNTAX LldpXdot3RemPortNeighborsEntry
			MAX-ACCESS not-accessible
			STATUS current
			DESCRIPTION
				"Description."
			INDEX { lldpXdot3RemPortInex, lldpXdot3RemPortNeighborsIndex }
			::= { lldpXdot3RemPortNeighborsTable 1 }

		
		LldpXdot3RemPortNeighborsEntry ::=
			SEQUENCE { 
				lldpXdot3RemPortInex
					Integer32,
				lldpXdot3RemPortNeighborsIndex
					Integer32,
				lldpXdot3RemPortNeighborsChassisType
					OCTET STRING,
				lldpXdot3RemPortNeighborsChassisID
					OCTET STRING,
				lldpXdot3RemPortNeighborsPortType
					INTEGER,
				lldpXdot3RemPortNeighborsPortID
					OCTET STRING,
				lldpXdot3RemPortNeighborsPortDesc
					OCTET STRING,
				lldpXdot3RemPortNeighborsSystemName
					OCTET STRING,
				lldpXdot3RemPortNeighborsSystemDesc
					OCTET STRING,
				lldpXdot3RemPortNeighborsSystemCapSupported
					OCTET STRING,
				lldpXdot3RemPortNeighborsSystemCapEnable
					OCTET STRING,
				lldpXdot3RemPortNeighborsManageAddrType
					INTEGER,
				lldpXdot3RemPortNeighborsManageAddr
					OCTET STRING,
				lldpXdot3RemPortNeighborsManageAddrInterType
					OCTET STRING,
				lldpXdot3RemPortNeighborsManageAddrInterID
					Integer32,
				lldpXdot3RemPortNeighborsManageAddrInterOid
					Integer32,
				lldpXdot3RemPortNeighborsExpiredTime
					Integer32,
				lldpXdot3RemPortNeighborsPvid
					Integer32,
				lldpXdot3RemPortNeighborsPpvid
					Integer32,
				lldpXdot3RemPortNeighborsPpvidSupported
					INTEGER,
				lldpXdot3RemPortNeighborsPpvidEnable
					INTEGER,
				lldpXdot3RemPortNeighborsVlanName
					OCTET STRING,
				lldpXdot3RemPortNeighborsAutoNegSupported
					INTEGER,
				lldpXdot3RemPortNeighborsAutoNegEnable
					INTEGER,
				lldpXdot3RemPortNeighborsOperMau
					OCTET STRING,
				lldpXdot3RemPortNeighborsPowerPortClass
					INTEGER,
				lldpXdot3RemPortNeighborsPseSupported
					INTEGER,
				lldpXdot3RemPortNeighborsPseEnable
					INTEGER,
				lldpXdot3RemPortNeighborsPsePairsCtrlAbility
					INTEGER,
				lldpXdot3RemPortNeighborsPowerPairs
					OCTET STRING,
				lldpXdot3RemPortNeighborsPortPowerClassification
					OCTET STRING,
				lldpXdot3RemPortNeighborsLagSupported
					INTEGER,
				lldpXdot3RemPortNeighborsLagEnable
					INTEGER,
				lldpXdot3RemPortNeighborsAggregationPortId
					Integer32,
				lldpXdot3RemPortNeighborsMaxFrameSize
					Integer32
			 }

		-- 1.3.6.1.4.1.34592.1.3.100.24.1.1.1
		lldpXdot3RemPortInex OBJECT-TYPE
			SYNTAX Integer32
			MAX-ACCESS not-accessible
			STATUS current
			DESCRIPTION
				"Description."
			::= { lldpXdot3RemPortNeighborsEntry 1 }

		
		-- 1.3.6.1.4.1.34592.1.3.100.24.1.1.2
		lldpXdot3RemPortNeighborsIndex OBJECT-TYPE
			SYNTAX Integer32
			MAX-ACCESS not-accessible
			STATUS current
			DESCRIPTION
				"Description."
			::= { lldpXdot3RemPortNeighborsEntry 2 }

		
		-- 1.3.6.1.4.1.34592.1.3.100.24.1.1.3
		lldpXdot3RemPortNeighborsChassisType OBJECT-TYPE
			SYNTAX OCTET STRING
			MAX-ACCESS read-only
			STATUS current
			DESCRIPTION
				"Description."
			::= { lldpXdot3RemPortNeighborsEntry 3 }

		
		-- 1.3.6.1.4.1.34592.1.3.100.24.1.1.4
		lldpXdot3RemPortNeighborsChassisID OBJECT-TYPE
			SYNTAX OCTET STRING
			MAX-ACCESS read-only
			STATUS current
			DESCRIPTION
				"Description."
			::= { lldpXdot3RemPortNeighborsEntry 4 }

		
		-- 1.3.6.1.4.1.34592.1.3.100.24.1.1.5
		lldpXdot3RemPortNeighborsPortType OBJECT-TYPE
			SYNTAX INTEGER
				{
				InterfaceName(1),
				MACAddress(2)
				}
			MAX-ACCESS read-only
			STATUS current
			DESCRIPTION
				"Description."
			::= { lldpXdot3RemPortNeighborsEntry 5 }

		
		-- 1.3.6.1.4.1.34592.1.3.100.24.1.1.6
		lldpXdot3RemPortNeighborsPortID OBJECT-TYPE
			SYNTAX OCTET STRING
			MAX-ACCESS read-only
			STATUS current
			DESCRIPTION
				"Description."
			::= { lldpXdot3RemPortNeighborsEntry 6 }

		
		-- 1.3.6.1.4.1.34592.1.3.100.24.1.1.7
		lldpXdot3RemPortNeighborsPortDesc OBJECT-TYPE
			SYNTAX OCTET STRING
			MAX-ACCESS read-only
			STATUS current
			DESCRIPTION
				"Description."
			::= { lldpXdot3RemPortNeighborsEntry 7 }

		
		-- 1.3.6.1.4.1.34592.1.3.100.24.1.1.8
		lldpXdot3RemPortNeighborsSystemName OBJECT-TYPE
			SYNTAX OCTET STRING
			MAX-ACCESS read-only
			STATUS current
			DESCRIPTION
				"Description."
			::= { lldpXdot3RemPortNeighborsEntry 8 }

		
		-- 1.3.6.1.4.1.34592.1.3.100.24.1.1.9
		lldpXdot3RemPortNeighborsSystemDesc OBJECT-TYPE
			SYNTAX OCTET STRING
			MAX-ACCESS read-only
			STATUS current
			DESCRIPTION
				"Description."
			::= { lldpXdot3RemPortNeighborsEntry 9 }

		
		-- 1.3.6.1.4.1.34592.1.3.100.24.1.1.10
		lldpXdot3RemPortNeighborsSystemCapSupported OBJECT-TYPE
			SYNTAX OCTET STRING
			MAX-ACCESS read-only
			STATUS current
			DESCRIPTION
				"Description."
			::= { lldpXdot3RemPortNeighborsEntry 10 }

		
		-- 1.3.6.1.4.1.34592.1.3.100.24.1.1.11
		lldpXdot3RemPortNeighborsSystemCapEnable OBJECT-TYPE
			SYNTAX OCTET STRING
			MAX-ACCESS read-only
			STATUS current
			DESCRIPTION
				"Description."
			::= { lldpXdot3RemPortNeighborsEntry 11 }

		
		-- 1.3.6.1.4.1.34592.1.3.100.24.1.1.12
		lldpXdot3RemPortNeighborsManageAddrType OBJECT-TYPE
			SYNTAX INTEGER
				{
				Other(0),
				ipv4(1),
				All802(2)
				}
			MAX-ACCESS read-only
			STATUS current
			DESCRIPTION
				"Description."
			::= { lldpXdot3RemPortNeighborsEntry 12 }

		
		-- 1.3.6.1.4.1.34592.1.3.100.24.1.1.13
		lldpXdot3RemPortNeighborsManageAddr OBJECT-TYPE
			SYNTAX OCTET STRING
			MAX-ACCESS read-only
			STATUS current
			DESCRIPTION
				"Description."
			::= { lldpXdot3RemPortNeighborsEntry 13 }

		
		-- 1.3.6.1.4.1.34592.1.3.100.24.1.1.14
		lldpXdot3RemPortNeighborsManageAddrInterType OBJECT-TYPE
			SYNTAX OCTET STRING
			MAX-ACCESS read-only
			STATUS current
			DESCRIPTION
				"Description."
			::= { lldpXdot3RemPortNeighborsEntry 14 }

		
		-- 1.3.6.1.4.1.34592.1.3.100.24.1.1.15
		lldpXdot3RemPortNeighborsManageAddrInterID OBJECT-TYPE
			SYNTAX Integer32
			MAX-ACCESS read-only
			STATUS current
			DESCRIPTION
				"Description."
			::= { lldpXdot3RemPortNeighborsEntry 15 }

		
		-- 1.3.6.1.4.1.34592.1.3.100.24.1.1.16
		lldpXdot3RemPortNeighborsManageAddrInterOid OBJECT-TYPE
			SYNTAX Integer32
			MAX-ACCESS read-only
			STATUS current
			DESCRIPTION
				"Description."
			::= { lldpXdot3RemPortNeighborsEntry 16 }

		
		-- 1.3.6.1.4.1.34592.1.3.100.24.1.1.17
		lldpXdot3RemPortNeighborsExpiredTime OBJECT-TYPE
			SYNTAX Integer32
			MAX-ACCESS read-only
			STATUS current
			DESCRIPTION
				"Description."
			::= { lldpXdot3RemPortNeighborsEntry 17 }

		
		-- 1.3.6.1.4.1.34592.1.3.100.24.1.1.18
		lldpXdot3RemPortNeighborsPvid OBJECT-TYPE
			SYNTAX Integer32
			MAX-ACCESS read-only
			STATUS current
			DESCRIPTION
				"Description."
			::= { lldpXdot3RemPortNeighborsEntry 18 }

		
		-- 1.3.6.1.4.1.34592.1.3.100.24.1.1.19
		lldpXdot3RemPortNeighborsPpvid OBJECT-TYPE
			SYNTAX Integer32
			MAX-ACCESS read-only
			STATUS current
			DESCRIPTION
				"Description."
			::= { lldpXdot3RemPortNeighborsEntry 19 }

		
		-- 1.3.6.1.4.1.34592.1.3.100.24.1.1.20
		lldpXdot3RemPortNeighborsPpvidSupported OBJECT-TYPE
			SYNTAX INTEGER
				{
				NO(0),
				YES(1)
				}
			MAX-ACCESS read-only
			STATUS current
			DESCRIPTION
				"Description."
			::= { lldpXdot3RemPortNeighborsEntry 20 }

		
		-- 1.3.6.1.4.1.34592.1.3.100.24.1.1.21
		lldpXdot3RemPortNeighborsPpvidEnable OBJECT-TYPE
			SYNTAX INTEGER
				{
				NO(0),
				YES(1)
				}
			MAX-ACCESS read-only
			STATUS current
			DESCRIPTION
				"Description."
			::= { lldpXdot3RemPortNeighborsEntry 21 }

		
		-- 1.3.6.1.4.1.34592.1.3.100.24.1.1.22
		lldpXdot3RemPortNeighborsVlanName OBJECT-TYPE
			SYNTAX OCTET STRING
			MAX-ACCESS read-only
			STATUS current
			DESCRIPTION
				"Description."
			::= { lldpXdot3RemPortNeighborsEntry 22 }

		
		-- 1.3.6.1.4.1.34592.1.3.100.24.1.1.23
		lldpXdot3RemPortNeighborsAutoNegSupported OBJECT-TYPE
			SYNTAX INTEGER
				{
				NO(0),
				YES(1)
				}
			MAX-ACCESS read-only
			STATUS current
			DESCRIPTION
				"Description."
			::= { lldpXdot3RemPortNeighborsEntry 23 }

		
		-- 1.3.6.1.4.1.34592.1.3.100.24.1.1.24
		lldpXdot3RemPortNeighborsAutoNegEnable OBJECT-TYPE
			SYNTAX INTEGER
				{
				NO(0),
				YES(1)
				}
			MAX-ACCESS read-only
			STATUS current
			DESCRIPTION
				"Description."
			::= { lldpXdot3RemPortNeighborsEntry 24 }

		
		-- 1.3.6.1.4.1.34592.1.3.100.24.1.1.25
		lldpXdot3RemPortNeighborsOperMau OBJECT-TYPE
			SYNTAX OCTET STRING
			MAX-ACCESS read-only
			STATUS current
			DESCRIPTION
				"Description."
			::= { lldpXdot3RemPortNeighborsEntry 25 }

		
		-- 1.3.6.1.4.1.34592.1.3.100.24.1.1.26
		lldpXdot3RemPortNeighborsPowerPortClass OBJECT-TYPE
			SYNTAX INTEGER
				{
				PD(0),
				PSE(1)
				}
			MAX-ACCESS read-only
			STATUS current
			DESCRIPTION
				"Description."
			::= { lldpXdot3RemPortNeighborsEntry 26 }

		
		-- 1.3.6.1.4.1.34592.1.3.100.24.1.1.27
		lldpXdot3RemPortNeighborsPseSupported OBJECT-TYPE
			SYNTAX INTEGER
				{
				NO(0),
				YES(1)
				}
			MAX-ACCESS read-only
			STATUS current
			DESCRIPTION
				"Description."
			::= { lldpXdot3RemPortNeighborsEntry 27 }

		
		-- 1.3.6.1.4.1.34592.1.3.100.24.1.1.28
		lldpXdot3RemPortNeighborsPseEnable OBJECT-TYPE
			SYNTAX INTEGER
				{
				NO(0),
				YES(1)
				}
			MAX-ACCESS read-only
			STATUS current
			DESCRIPTION
				"Description."
			::= { lldpXdot3RemPortNeighborsEntry 28 }

		
		-- 1.3.6.1.4.1.34592.1.3.100.24.1.1.29
		lldpXdot3RemPortNeighborsPsePairsCtrlAbility OBJECT-TYPE
			SYNTAX INTEGER
				{
				NO(0),
				YES(1)
				}
			MAX-ACCESS read-only
			STATUS current
			DESCRIPTION
				"Description."
			::= { lldpXdot3RemPortNeighborsEntry 29 }

		
		-- 1.3.6.1.4.1.34592.1.3.100.24.1.1.30
		lldpXdot3RemPortNeighborsPowerPairs OBJECT-TYPE
			SYNTAX OCTET STRING
			MAX-ACCESS read-only
			STATUS current
			DESCRIPTION
				"Description."
			::= { lldpXdot3RemPortNeighborsEntry 30 }

		
		-- 1.3.6.1.4.1.34592.1.3.100.24.1.1.31
		lldpXdot3RemPortNeighborsPortPowerClassification OBJECT-TYPE
			SYNTAX OCTET STRING
			MAX-ACCESS read-only
			STATUS current
			DESCRIPTION
				"Description."
			::= { lldpXdot3RemPortNeighborsEntry 31 }

		
		-- 1.3.6.1.4.1.34592.1.3.100.24.1.1.32
		lldpXdot3RemPortNeighborsLagSupported OBJECT-TYPE
			SYNTAX INTEGER
				{
				NO(0),
				YES(1)
				}
			MAX-ACCESS read-only
			STATUS current
			DESCRIPTION
				"Description."
			::= { lldpXdot3RemPortNeighborsEntry 32 }

		
		-- 1.3.6.1.4.1.34592.1.3.100.24.1.1.33
		lldpXdot3RemPortNeighborsLagEnable OBJECT-TYPE
			SYNTAX INTEGER
				{
				NO(0),
				YES(1)
				}
			MAX-ACCESS read-only
			STATUS current
			DESCRIPTION
				"Description."
			::= { lldpXdot3RemPortNeighborsEntry 33 }

		
		-- 1.3.6.1.4.1.34592.1.3.100.24.1.1.34
		lldpXdot3RemPortNeighborsAggregationPortId OBJECT-TYPE
			SYNTAX Integer32
			MAX-ACCESS read-only
			STATUS current
			DESCRIPTION
				"Description."
			::= { lldpXdot3RemPortNeighborsEntry 34 }

		
		-- 1.3.6.1.4.1.34592.1.3.100.24.1.1.35
		lldpXdot3RemPortNeighborsMaxFrameSize OBJECT-TYPE
			SYNTAX Integer32
			MAX-ACCESS read-only
			STATUS current
			DESCRIPTION
				"Description."
			::= { lldpXdot3RemPortNeighborsEntry 35 }

	END

--
-- NSCRTV-PON-TREE-EXT-MIB.my
--
